;; Coloca os blocos segundo a descrição 
(defun c:morada(/)
(princ "********* Espere um pouco - processando dados  ***********")
(setq olcmdecho (getvar "cmdecho"))
(setvar "cmdecho" 0)
(command "_.insert" "INCRA_vertice_P" "197180.8428,8265600.573" "1" "" "0" "P1" "")
(command "_.insert" "INCRA_vertice_P" "197190.3224,8265593.153" "1" "" "0" "P2" "")
(command "_.insert" "INCRA_vertice_P" "197201.6138,8265584.315" "1" "" "0" "P3" "")
(command "_.insert" "INCRA_vertice_P" "197212.4389,8265575.843" "1" "" "0" "P4" "")
(command "_.insert" "INCRA_vertice_P" "197224.1644,8265566.665" "1" "" "0" "P5" "")
(command "_.insert" "INCRA_vertice_P" "197245.7776,8265594.09" "1" "" "0" "P6" "")
(command "_.insert" "INCRA_vertice_P" "197246.2311,8265594.666" "1" "" "0" "P7" "")
(command "_.insert" "INCRA_vertice_P" "197257.5792,8265585.88" "1" "" "0" "P8" "")
(command "_.insert" "INCRA_vertice_P" "197268.6325,8265577.127" "1" "" "0" "P9" "")
(command "_.insert" "INCRA_vertice_P" "197280.194,8265567.971" "1" "" "0" "P10" "")
(command "_.insert" "INCRA_vertice_P" "197291.3157,8265559.163" "1" "" "0" "P11" "")
(command "_.insert" "INCRA_vertice_P" "197291.3313,8265559.151" "1" "" "0" "P12" "")
(command "_.insert" "INCRA_vertice_P" "197302.2229,8265550.666" "1" "" "0" "P13" "")
(command "_.insert" "INCRA_vertice_P" "197280.4036,8265522.646" "1" "" "0" "P14" "")
(command "_.insert" "INCRA_vertice_P" "197291.8419,8265513.693" "1" "" "0" "P15" "")
(command "_.insert" "INCRA_vertice_P" "197303.4031,8265505.049" "1" "" "0" "P16" "")
(command "_.insert" "INCRA_vertice_P" "197314.5561,8265496.249" "1" "" "0" "P17" "")
(command "_.insert" "INCRA_vertice_P" "197325.6893,8265487.464" "1" "" "0" "P18" "")
(command "_.insert" "INCRA_vertice_P" "197337.0189,8265478.583" "1" "" "0" "P19" "")
(command "_.insert" "INCRA_vertice_P" "197345.1166,8265472.827" "1" "" "0" "P20" "")
(command "_.insert" "INCRA_vertice_P" "197356.5398,8265463.876" "1" "" "0" "P21" "")
(command "_.insert" "INCRA_vertice_P" "197367.963,8265454.926" "1" "" "0" "P22" "")
(command "_.insert" "INCRA_vertice_P" "197379.1475,8265446.162" "1" "" "0" "P23" "")
(command "_.insert" "INCRA_vertice_P" "197390.332,8265437.399" "1" "" "0" "P24" "")
(command "_.insert" "INCRA_vertice_P" "197401.5413,8265428.667" "1" "" "0" "P25" "")
(command "_.insert" "INCRA_vertice_P" "197412.7507,8265419.935" "1" "" "0" "P26" "")
(command "_.insert" "INCRA_vertice_P" "197423.9145,8265411.238" "1" "" "0" "P27" "")
(command "_.insert" "INCRA_vertice_P" "197435.2952,8265402.373" "1" "" "0" "P28" "")
(command "_.insert" "INCRA_vertice_P" "197413.7434,8265374.59" "1" "" "0" "P29" "")
(command "_.insert" "INCRA_vertice_P" "197436.1778,8265357.032" "1" "" "0" "P30" "")
(command "_.insert" "INCRA_vertice_P" "197447.5689,8265348.117" "1" "" "0" "P31" "")
(command "_.insert" "INCRA_vertice_P" "197453.6124,8265343.388" "1" "" "0" "P32" "")
(command "_.insert" "INCRA_vertice_P" "197482.6333,8265320.659" "1" "" "0" "P33" "")
(command "_.insert" "INCRA_vertice_P" "197499.6754,8265307.357" "1" "" "0" "P34" "")
(command "_.insert" "INCRA_vertice_P" "197510.9163,8265298.583" "1" "" "0" "P35" "")
(command "_.insert" "INCRA_vertice_P" "197522.2013,8265289.774" "1" "" "0" "P36" "")
(command "_.insert" "INCRA_vertice_P" "197523.6629,8265288.633" "1" "" "0" "P37" "")
(command "_.insert" "INCRA_vertice_P" "197533.5235,8265280.936" "1" "" "0" "P38" "")
(command "_.insert" "INCRA_vertice_P" "197556.0865,8265263.324" "1" "" "0" "P39" "")
(command "_.insert" "INCRA_vertice_P" "197570.0422,8265252.431" "1" "" "0" "P40" "")
(command "_.insert" "INCRA_vertice_P" "197605.1449,8265219.493" "1" "" "0" "P41" "")
(command "_.insert" "INCRA_vertice_P" "197540.6694,8265172.815" "1" "" "0" "P42" "")
(command "_.insert" "INCRA_vertice_P" "197465.7385,8265118.149" "1" "" "0" "P43" "")
(command "_.insert" "INCRA_vertice_P" "197433.7292,8265094.862" "1" "" "0" "P44" "")
(command "_.insert" "INCRA_vertice_P" "197397.2093,8265068.537" "1" "" "0" "P45" "")
(command "_.insert" "INCRA_vertice_P" "197352.7093,8265036.186" "1" "" "0" "P46" "")
(command "_.insert" "INCRA_vertice_P" "197313.7238,8265047.965" "1" "" "0" "P47" "")
(command "_.insert" "INCRA_vertice_P" "197166.5218,8265095.906" "1" "" "0" "P48" "")
(command "_.insert" "INCRA_vertice_P" "197008.6994,8264976.473" "1" "" "0" "P49" "")
(command "_.insert" "INCRA_vertice_P" "197155.7892,8264932.139" "1" "" "0" "P50" "")
(command "_.insert" "INCRA_vertice_P" "197155.1126,8264931.62" "1" "" "0" "P51" "")
(command "_.insert" "INCRA_vertice_P" "197187.6385,8264922.295" "1" "" "0" "P52" "")
(command "_.insert" "INCRA_vertice_P" "197131.3622,8264883.059" "1" "" "0" "P53" "")
(command "_.insert" "INCRA_vertice_P" "197089.1755,8264853.876" "1" "" "0" "P54" "")
(command "_.insert" "INCRA_vertice_P" "197049.6024,8264826.584" "1" "" "0" "P55" "")
(command "_.insert" "INCRA_vertice_P" "197014.1487,8264804.701" "1" "" "0" "P56" "")
(command "_.insert" "INCRA_vertice_P" "196996.735,8264796.259" "1" "" "0" "P57" "")
(command "_.insert" "INCRA_vertice_P" "196975.4673,8264793.649" "1" "" "0" "P58" "")
(command "_.insert" "INCRA_vertice_P" "196900.0907,8264813.443" "1" "" "0" "P59" "")
(command "_.insert" "INCRA_vertice_P" "196888.5362,8264816.658" "1" "" "0" "P60" "")
(command "_.insert" "INCRA_vertice_P" "196867.2237,8264822.194" "1" "" "0" "P61" "")
(command "_.insert" "INCRA_vertice_P" "196832.0333,8264835.784" "1" "" "0" "P62" "")
(command "_.insert" "INCRA_vertice_P" "196798.9523,8264848.27" "1" "" "0" "P63" "")
(command "_.insert" "INCRA_vertice_P" "196782.5552,8264858.095" "1" "" "0" "P64" "")
(command "_.insert" "INCRA_vertice_P" "196718.6801,8264897.133" "1" "" "0" "P65" "")
(command "_.insert" "INCRA_vertice_P" "196673.7229,8264924.693" "1" "" "0" "P66" "")
(command "_.insert" "INCRA_vertice_P" "196658.2361,8264947.481" "1" "" "0" "P67" "")
(command "_.insert" "INCRA_vertice_P" "196684.0344,8264974.421" "1" "" "0" "P68" "")
(command "_.insert" "INCRA_vertice_P" "196691.9664,8264982.773" "1" "" "0" "P69" "")
(command "_.insert" "INCRA_vertice_P" "196703.902,8264994.684" "1" "" "0" "P70" "")
(command "_.insert" "INCRA_vertice_P" "196680.146,8265019.659" "1" "" "0" "P71" "")
(command "_.insert" "INCRA_vertice_P" "196705.1023,8265044.083" "1" "" "0" "P72" "")
(command "_.insert" "INCRA_vertice_P" "196729.7446,8265067.982" "1" "" "0" "P73" "")
(command "_.insert" "INCRA_vertice_P" "196742.2651,8265079.056" "1" "" "0" "P74" "")
(command "_.insert" "INCRA_vertice_P" "196758.8445,8265095.306" "1" "" "0" "P75" "")
(command "_.insert" "INCRA_vertice_P" "196779.3087,8265065.94" "1" "" "0" "P76" "")
(command "_.insert" "INCRA_vertice_P" "196974.084,8265256.065" "1" "" "0" "P77" "")
(command "_.insert" "INCRA_vertice_P" "197000.5819,8265280.205" "1" "" "0" "P78" "")
(command "_.insert" "INCRA_vertice_P" "197197.0733,8265265.252" "1" "" "0" "P79" "")
(command "_.insert" "INCRA_vertice_P" "197200.3222,8265270.705" "1" "" "0" "P80" "")
(command "_.insert" "INCRA_vertice_P" "197202.7222,8265271.396" "1" "" "0" "P81" "")
(command "_.insert" "INCRA_vertice_P" "197252.832,8265353.012" "1" "" "0" "P82" "")
(command "_.insert" "INCRA_vertice_P" "197307.4551,8265441.788" "1" "" "0" "P83" "")
(command "_.insert" "INCRA_vertice_P" "197151.1093,8265563.351" "1" "" "0" "P84" "")
(command "_.insert" "INCRA_vertice_P" "197180.8428,8265600.573" "1" "" "0" "P1" "")
(setvar "cmdecho" olcmdecho)
(setvar "clayer" oldlayer)
(princ)
)
(princ "\nDigite 'morada' para iniciar")
