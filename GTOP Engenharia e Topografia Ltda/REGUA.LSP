(defun C:LEROY (/ h)
 (prompt "\nAJUSTA AS LETRAS COM O PADRAO LEROY")
 (initget 1  "40 50 60 80 100 120 140 175 200")
 (setq regua (getint "\nTamanho da Regua (40 50 60 80 100 120 140 175 200): ")
       escala (getreal "Escala do desenho: ")
 )
 (cond ((= regua  40) (setq h 1.0))
       ((= regua  50) (setq h 1.3))
       ((= regua  60) (setq h 1.6))
       ((= regua  80) (setq h 2.0))
       ((= regua 100) (setq h 2.5))
       ((= regua 120) (setq h 3.0))
       ((= regua 140) (setq h 3.5))
       ((= regua 175) (setq h 4.0))
       ((= regua 200) (setq h 4.5))
 )
 (setq fator (/ escala 1000))
 (if (< regua 201)
   (setvar "textsize" (* h fator))
   (setvar "textsize" 1.6)
  )
)
(princ "\nDigite 'LEROY' para iniciar")
