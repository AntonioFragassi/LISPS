;; Coloca os blocos segundo a descrição 

(defun c:blkseduh( / olcmdecho oldlayer escala Conjunto_INSERT Comp_Conjunto Objeto ponto lista  Attn Attv diam)
(princ "********* Espere um pouco - processando dados  ***********")
(setq oldangbase (getvar "angbase"));;correção 2
(setvar "angbase" 0.0)
(setq oldangdir (getvar "angdir"));;correção 2
(setvar "angdir" 0)
(setq oldosmode (getvar "osmode"))
(setvar "osmode" 0)
(setq oldcmdecho (getvar "cmdecho"))
(setvar "cmdecho" 0)
(setq oldlayer (getvar "clayer"))
(setq escala (getreal "Escala do desenho: "))
(setq escala (/ escala 1000.0))
(setq Conjunto_INSERT (ssget '((0 . "INSERT"))))
(if Conjunto_INSERT ;; primeiro if
    (progn 
	(setq Comp_Conjunto (sslength Conjunto_INSERT))
	(while (> Comp_Conjunto 0) ;; primeiro while
	    (setq Comp_Conjunto (1- Comp_Conjunto))
	    (setq Objeto (ssname Conjunto_INSERT  Comp_Conjunto))
        (setq ponto (cdr (assoc 10 (entget Objeto))))
 	    (while (/= (cdr (assoc 0 (entget OBJETO))) "SEQEND")
        (setq OBJETO (entnext OBJETO))
  		(setq lista (entget OBJETO))
       	(setq Attn (cdr (assoc 2 lista)))
  		(setq Attv (cdr (assoc 1 lista)))
        	(if (= Attn "DESC")
	            (progn
		                (setq desc (substr Attv 4 ))
		        	    (setq Attv (substr Attv 1 3))
                           (cond
											((= Attv "ANT") (progn (command "_.layer" "m" "TOP-ANTENA" "") (command "_.insert" "A$C42EF300E" ponto escala "" "0" "")))
											((= Attv "APG") (progn (command "_.layer" "m" "TOP-AP. GINASTICA" "") (command "_.insert" "A$C5D413A16" ponto escala "" "0" "")))
											((= Attv "ARV") (progn (command "_.layer" "m" "TOP-ÁRVORE" "") (command "_.insert" "A$C49782D5F" ponto escala "" "0" "")))
											((= Attv "COQ") (progn (command "_.layer" "m" "TOP-ÁRVORE_COQUEIRO" "") (command "_.insert" "A$C2AAA6732" ponto escala "" "0" "")))
											((= Attv "PAL") (progn (command "_.layer" "m" "TOP-ÁRVORE_PALMEIRA" "") (command "_.insert" "A$C3EA7075F" ponto escala "" "0" "")))
											((= Attv "PIN") (progn (command "_.layer" "m" "TOP-ÁRVORE_PINHEIRO" "") (command "_.insert" "A$C32BC4519" ponto escala "" "0" "")))
											((= Attv "TOC") (progn (command "_.layer" "m" "TOP-ÁRVORE_TOCO" "") (command "_.insert" "A$C6FF31F83" ponto escala "" "0" "")))
											((= Attv "BAL") (progn (command "_.layer" "m" "TOP-BALIZADOR" "") (command "_.insert" "A$C60A577F8" ponto escala "" "0" "")))
											((= Attv "CIS") (progn (command "_.layer" "m" "TOP-CAIXA INSPEÇÃO SEM IDENTIFICAÇÃO" "") (command "_.insert" "A$C12260DE9" ponto escala "" "0" "")))
											((= Attv "LIX") (progn (command "_.layer" "m" "TOP-LIXEIRA" "") (command "_.insert" "A$C6D961FD8" ponto escala "" "0" "")))
											((= Attv "MDP") (progn (command "_.layer" "m" "TOP-MUDA DE PLANTA" "") (command "_.insert" "A$C573F1E39" ponto escala "" "0" "")))
											((= Attv "PLA") (progn (command "_.layer" "m" "TOP-PLACA" "") (command "_.insert" "A$C34343D36" ponto escala "" "0" "")))
											((= Attv "PLS") (progn (command "_.layer" "m" "TOP-PLACA-SINALIZAÇÃO" "") (command "_.insert" "A$C0EAB5E08" ponto escala "" "0" "")))
											((= Attv "PVN") (progn (command "_.layer" "m" "TOP-POÇO DE VISITA NÃO IDENTIFICADO" "") (command "_.insert" "A$C4DA813CF" ponto escala "" "0" "")))
											((= Attv "CHD") (progn (command "_.layer" "m" "TOP-REDE ÁGUA POTÁVEL_CAIXA-HIDRANTE" "") (command "_.insert" "A$C222801AC" ponto escala "" "0" "")))
											((= Attv "HID") (progn (command "_.layer" "m" "TOP-REDE ÁGUA POTÁVEL_HIDRANTE" "") (command "_.insert" "A$C0BEB5EB6" ponto escala "" "0" "")))
											((= Attv "RGA") (progn (command "_.layer" "m" "TOP-REDE ÁGUA POTÁVEL_REGISTRO" "") (command "_.insert" "A$C25073941" ponto escala "" "0" "")))
											((= Attv "TOR") (progn (command "_.layer" "m" "TOP-REDE ÁGUA POTÁVEL_TORNEIRA" "") (command "_.insert" "A$C233C3A97" ponto escala "" "0" "")))
											((= Attv "BOL") (progn (command "_.layer" "m" "TOP-REDE ÁGUAS PLUVIAIS_BOCA DE LOBO" "") (command "_.insert" "A$C654D5053" ponto escala "" "0" "")))
											((= Attv "GRE") (progn (command "_.layer" "m" "TOP-REDE ÁGUAS PLUVIAIS_BOCA DE LOBO-GRELHA" "") (command "_.insert" "A$C7CFE4D38" ponto escala "" "0" "")))
											((= Attv "PVA") (progn (command "_.layer" "m" "TOP-REDE ÁGUAS PLUVIAIS_POÇO DE VISITA" "") (command "_.insert" "A$C13FD63B8" ponto escala "" "0" "")))
											((= Attv "CXE") (progn (command "_.layer" "m" "TOP-REDE ELÉTRICA_CAIXA DE INSPEÇÃO" "") (command "_.insert" "A$C29C304B7" ponto escala "" "0" "")))
											((= Attv "CXD") (progn (command "_.layer" "m" "TOP-REDE ELÉTRICA_CAIXA DETRAN" "") (command "_.insert" "A$C3AFF17E5" ponto escala "" "0" "")))
											((= Attv "LUM") (progn (command "_.layer" "m" "TOP-REDE ELÉTRICA_LUMINÁRIA-CONCRETO" "") (command "_.insert" "A$C325C66AC" ponto escala "" "0" "")))
											((= Attv "LUF") (progn (command "_.layer" "m" "TOP-REDE ELÉTRICA_LUMINÁRIA-FERRO" "") (command "_.insert" "A$C3EB44A8F" ponto escala "" "0" "")))
											((= Attv "LUJ") (progn (command "_.layer" "m" "TOP-REDE ELÉTRICA_LUMINÁRIA-FERRO-JARDIM" "") (command "_.insert" "A$C736F3E37" ponto escala "" "0" "")))
											((= Attv "PDE") (progn (command "_.layer" "m" "TOP-REDE ELÉTRICA_PADRÃO-ENERGIA" "") (command "_.insert" "A$C068917E8" ponto escala "" "0" "")))
											((= Attv "PVC") (progn (command "_.layer" "m" "TOP-REDE ELÉTRICA_POÇO DE VISITA" "") (command "_.insert" "A$C1B4B6171" ponto escala "" "0" "")))
											((= Attv "PVAT") (progn (command "_.layer" "m" "TOP-REDE ELÉTRICA_POÇO DE VISITA-ALTA TENSÃO" "") (command "_.insert" "A$C20376F33" ponto escala "" "0" "")))
											((= Attv "PVBT") (progn (command "_.layer" "m" "TOP-REDE ELÉTRICA_POÇO DE VISITA-BAIXA TENSÃO" "") (command "_.insert" "A$C6B3F577C" ponto escala "" "0" "")))
											((= Attv "POC") (progn (command "_.layer" "m" "TOP-REDE ELÉTRICA_POSTE-CONCRETO" "") (command "_.insert" "A$C4CAD4B8B" ponto escala "" "0" "")))
											((= Attv "POCA") (progn (command "_.layer" "m" "TOP-REDE ELÉTRICA_POSTE-CONCRETO-AMARRAÇÃO" "") (command "_.insert" "A$C7326432B" ponto escala "" "0" "")))
											((= Attv "PCL") (progn (command "_.layer" "m" "TOP-REDE ELÉTRICA_POSTE-CONCRETO-LUMINÁRIA" "") (command "_.insert" "A$C2E34311C" ponto escala "" "0" "")))
											((= Attv "PCTL") (progn (command "_.layer" "m" "TOP-REDE ELÉTRICA_POSTE-CONC-TRANSF-LUMIN" "") (command "_.insert" "A$C3C1A1D79" ponto escala "" "0" "")))
											((= Attv "PCT") (progn (command "_.layer" "m" "TOP-REDE ELÉTRICA_POSTE-CONC-TRANSFORMADOR" "") (command "_.insert" "A$C1B175940" ponto escala "" "0" "")))
											((= Attv "REF") (progn (command "_.layer" "m" "TOP-REDE ELÉTRICA_REFLETOR" "") (command "_.insert" "A$C01D1759F" ponto escala "" "0" "")))
											((= Attv "SEM") (progn (command "_.layer" "m" "TOP-REDE ELÉTRICA_SEMÁFORO" "") (command "_.insert" "A$C23B73C06" ponto escala "" "0" "")))
											((= Attv "SEM") (progn (command "_.layer" "m" "TOP-REDE ELÉTRICA_SENSOR" "") (command "_.insert" "A$C51E61586" ponto escala "" "0" "")))
											((= Attv "CIE") (progn (command "_.layer" "m" "TOP-REDE ESGOTO_CAIXA DE INSPEÇÃO" "") (command "_.insert" "A$C0F2448E0" ponto escala "" "0" "")))
											((= Attv "PVE") (progn (command "_.layer" "m" "TOP-REDE ESGOTO_POÇO DE VISITA" "") (command "_.insert" "A$C55BD694A" ponto escala "" "0" "")))
											((= Attv "CXT") (progn (command "_.layer" "m" "TOP-REDE TELEFONICA_CAIXA DE INSPEÇÃO" "") (command "_.insert" "A$C6FD4223E" ponto escala "" "0" "")))
											((= Attv "CXI") (progn (command "_.layer" "m" "TOP-REDE TELEFONICA_CAIXA-INTERNET" "") (command "_.insert" "A$C3F6D74D9" ponto escala "" "0" "")))
											((= Attv "PVT") (progn (command "_.layer" "m" "TOP-REDE TELEFONICA_POÇO DE VISITA" "") (command "_.insert" "A$C128A16B0" ponto escala "" "0" "")))
											((= Attv "TLP") (progn (command "_.layer" "m" "TOP-REDE TELEFONICA_TELEFONE PÚBLICO" "") (command "_.insert" "A$C0DB759EB" ponto escala "" "0" "")))
                        );;fim do cond
		           );;fim do progn
                      );;fim do if
	      );;fim do while
             );fim do while
      );fim do progn
) ;;fim do primeiro if
(setvar "angdir" oldangdir)
(setvar "osmode" oldosmode)
(setvar "cmdecho" oldcmdecho)
(princ)
)
(princ "\nDigite 'blkseduh' para iniciar")
