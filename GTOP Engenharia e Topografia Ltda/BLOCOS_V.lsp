;; Coloca os blocos segundo a descrição 
(defun c:BLOCOSV(/)
(princ "********* Espere um pouco - processando dados  ***********")
(setq olcmdecho (getvar "cmdecho"))
(setvar "cmdecho" 0)
(command "_.insert" "INCRA_vertice_V" "217977.49,8243731.41" "1" "" "0" "A0D-V-MPJ0001" "")
(command "_.insert" "INCRA_vertice_V" "217979.46,8243710.7" "1" "" "0" "A0D-M-MPJ0001" "")
(command "_.insert" "INCRA_vertice_V" "217989.85,8243601.53" "1" "" "0" "A0D-M-MPJ0002" "")
(command "_.insert" "INCRA_vertice_V" "217989.49,8243590.76" "1" "" "0" "A0D-M-MPJ0003" "")
(command "_.insert" "INCRA_vertice_V" "217992.21,8243568.62" "1" "" "0" "A0D-M-MPJ0004" "")
(command "_.insert" "INCRA_vertice_V" "217970.1,8243571.18" "1" "" "0" "A0D-M-MPJ0005" "")
(command "_.insert" "INCRA_vertice_V" "217923.86,8243578.15" "1" "" "0" "A0D-M-MPJ0006" "")
(command "_.insert" "INCRA_vertice_V" "217873.7,8243574.54" "1" "" "0" "A0D-M-MPJ0007" "")
(command "_.insert" "INCRA_vertice_V" "217888.63,8243434.55" "1" "" "0" "A0D-M-MPJ0008" "")
(command "_.insert" "INCRA_vertice_V" "217748.22,8243463.98" "1" "" "0" "A0D-M-MPJ0009" "")
(command "_.insert" "INCRA_vertice_V" "217744.58,8243466.04" "1" "" "0" "A0D-M-MPJ0010" "")
(command "_.insert" "INCRA_vertice_V" "217732.41,8243456.59" "1" "" "0" "A0D-M-MPJ0011" "")
(command "_.insert" "INCRA_vertice_V" "217730.22,8243410.68" "1" "" "0" "A0D-M-MPJ0012" "")
(command "_.insert" "INCRA_vertice_V" "217721.73,8243423.62" "1" "" "0" "A0D-M-MPJ0013" "")
(command "_.insert" "INCRA_vertice_V" "217611,8243472.61" "1" "" "0" "A0D-M-MPJ0014" "")
(command "_.insert" "INCRA_vertice_V" "217603.17,8243643.31" "1" "" "0" "A0D-M-MPJ0015" "")
(command "_.insert" "INCRA_vertice_V" "217716.23,8243670.95" "1" "" "0" "YPUI-V-4140" "")
(command "_.insert" "INCRA_vertice_V" "217842.57,8243716.6" "1" "" "0" "A0D-V-MPJ0003" "")
(command "_.insert" "INCRA_vertice_V" "217942.82,8243726.68" "1" "" "0" "A0D-V-MPJ0004" "")
(setvar "cmdecho" olcmdecho)
(setvar "clayer" oldlayer)
(princ)
)
(princ "\nDigite 'BLOCOSV' para iniciar")
