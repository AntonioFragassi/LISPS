(Defun c:cria_layers (/)
;*************************************************************
;******************   Cria os  layers padrão *****************
;*************************************************************

;*************************************************************
;******  Cria tabela de layers no padrão MV TOPOGRAFIA *******
;*************************************************************
(command "_.STYLE" "ROMANS" "ROMANS" "0" "1.0" "0" "" "" "")
(command "_.STYLE" "standard" "ROMANS" "0" "1.0" "0" "" "" "")
(command "_.layer" "m" "SOLEIRA" "")
(command "_.layer" "m" "GERATRIZ" "")
(command "_.layer" "m" "CURVA_INTERMEDIARIA" "")
(command "_.layer" "m" "CURVA_MESTRA" "")
(command "_.layer" "m" "TXT_CURVA_MESTRA" "")
(command "_.layer" "m" "TXT_CURVA_INTERMEDIARIA" "")
(command "_.layer" "m" "TXT_GERATRIZ" "")
(command "_.layer" "m" "TXT_SOLEIRA" "")
(command "_.layer" "m" "LIMITE_DISTRITAL" "")
(command "_.layer" "m" "TXT_LIMITE_DISTRITAL" "")
(command "_.layer" "m" "TXT_LIMITE_POLIGONAL" "")
(command "_.layer" "m" "LIMITE_ESTADUAL" "")
(command "_.layer" "m" "TXT_LIMITE_ESTADUAL" "")
(command "_.layer" "m" "LIMITE_INTERNACIONAL" "")
(command "_.layer" "m" "TXT_LIMITE_INTERNACIONAL" "")
(command "_.layer" "m" "LIMITE_MUNICIPAL" "")
(command "_.layer" "m" "TXT_LIMITE_MUNICIPAL" "")
(command "_.layer" "m" "PERIMETRO_URBANO" "")
(command "_.layer" "m" "TXT_PERIMETRO_URBANO" "")
(command "_.layer" "m" "POLIGONAL_DE_ESTUDO" "")
(command "_.layer" "m" "TXT_POLIGONAL_DE_ESTUDO" "")
(command "_.layer" "m" "LIMITE_DE_PROPRIEDADE" "")
(command "_.layer" "m" "TXT_LIMITE_PROPRIEDADE" "")
(command "_.layer" "m" "TXT_LIMITE_BAIRRO" "")
(command "_.layer" "m" "TXT_LIMITE_QUADRA" "")
(command "_.layer" "m" "TXT_LIMITE_SETOR" "")
(command "_.layer" "m" "LIMITE_BAIRRO" "")
(command "_.layer" "m" "LIMITE_POLIGONAL" "")
(command "_.layer" "m" "LIMITE_QUADRA" "")
(command "_.layer" "m" "LIMITE_SETOR" "")
(command "_.layer" "m" "ALAMBRADO_GRADE" "")
(command "_.layer" "m" "CERCA_ARAME" "")
(command "_.layer" "m" "CERCA_MADEIRA" "")
(command "_.layer" "m" "CERCA_MISTA" "")
(command "_.layer" "m" "CERCA_VIVA" "")
(command "_.layer" "m" "MURO" "")
(command "_.layer" "m" "LOTE_TOPOGRAFICO" "")
(command "_.layer" "m" "TXT_LOTE_TOPOGRAFICO" "")
(command "_.layer" "m" "PORTAO" "")
(command "_.layer" "m" "MURETA" "")
(command "_.layer" "m" "TXT_MURETA" "")
(command "_.layer" "m" "TAPUME" "")
(command "_.layer" "m" "ALAGADO" "")
(command "_.layer" "m" "BREJO" "")
(command "_.layer" "m" "CACHOEIRA" "")
(command "_.layer" "m" "CANAL" "")
(command "_.layer" "m" "TXT_CANAL" "")
(command "_.layer" "m" "CORREDEIRA" "")
(command "_.layer" "m" "RIO_COR_INTERMITENTE" "")
(command "_.layer" "m" "TXT_RIO_COR_INTERMITENTE" "")
(command "_.layer" "m" "RIO_COR_PERENE" "")
(command "_.layer" "m" "TXT_RIO_COR_PERENE" "")
(command "_.layer" "m" "LAGO_LAGOA_INTERMITENTE" "")
(command "_.layer" "m" "TXT_LAGO_LAGOA_INTERMITENTE" "")
(command "_.layer" "m" "LAGO_LAGOA_PERENE" "")
(command "_.layer" "m" "TXT_LAGO_LAGOA_PERENE" "")
(command "_.layer" "m" "VALA" "")
(command "_.layer" "m" "FONTE_NASCENTE" "")
(command "_.layer" "m" "TXT_ALAGADO" "")
(command "_.layer" "m" "TXT_BREJO" "")
(command "_.layer" "m" "TXT_CACHOEIRA" "")
(command "_.layer" "m" "TXT_CORREDEIRA" "")
(command "_.layer" "m" "TXT_FONTE_NASCENTE" "")
(command "_.layer" "m" "TXT_GROTA" "")
(command "_.layer" "m" "TXT_POCO" "")
(command "_.layer" "m" "TXT_VALA" "")
(command "_.layer" "m" "GROTA" "")
(command "_.layer" "m" "POCO" "")
(command "_.layer" "m" "CAIXA_CORREIO" "")
(command "_.layer" "m" "LIXEIRA" "")
(command "_.layer" "m" "QUIOSQUE" "")
(command "_.layer" "m" "SEMAFORO" "")
(command "_.layer" "m" "TELEFONE_PUBLICO" "")
(command "_.layer" "m" "TELEFONE_PUBLICO_CABINE" "")
(command "_.layer" "m" "TXT_BANCO" "")
(command "_.layer" "m" "TXT_LIXEIRA" "")
(command "_.layer" "m" "TXT_PLACA_SINALIZACAO" "")
(command "_.layer" "m" "TXT_PONTO_ONIBUS" "")
(command "_.layer" "m" "TXT_PONTO_TAXI" "")
(command "_.layer" "m" "TXT_PLACA_PROPAGANDA" "")
(command "_.layer" "m" "TXT_QUIOSQUE" "")
(command "_.layer" "m" "TXT_SEMAFORO" "")
(command "_.layer" "m" "TXT_TELEFONE_PUBLICO" "")
(command "_.layer" "m" "TXT_TELEFONE_PUBLICO_CABINE" "")
(command "_.layer" "m" "TXT_BANCA_REVISTA" "")
(command "_.layer" "m" "BANCA_REVISTA" "")
(command "_.layer" "m" "BANCO" "")
(command "_.layer" "m" "PLACA_SINALIZACAO" "")
(command "_.layer" "m" "PLACA_PROPAGANDA" "")
(command "_.layer" "m" "PONTO_ONIBUS" "")
(command "_.layer" "m" "PONTO_TAXI" "")
(command "_.layer" "m" "TXT_CAIXA_CORREIO" "")
(command "_.layer" "m" "ARQUIBANCADA" "")
(command "_.layer" "m" "TXT_ARQUIBANCADA" "")
(command "_.layer" "m" "BARRAGEM_CONCRETO" "")
(command "_.layer" "m" "BARRAGEM_TERRA" "")
(command "_.layer" "m" "DIQUE" "")
(command "_.layer" "m" "ESCADARIA_RAMPA" "")
(command "_.layer" "m" "TXT_ESCADARIA_RAMPA" "")
(command "_.layer" "m" "GUARD_RAIL" "")
(command "_.layer" "m" "MURO_ARRIMO" "")
(command "_.layer" "m" "TXT_MURO_ARRIMO" "")
(command "_.layer" "m" "PASSAGEM_SUBTERRANEA" "")
(command "_.layer" "m" "TXT_PASSAGEM_SUBTERRANEA" "")
(command "_.layer" "m" "PASSARELA" "")
(command "_.layer" "m" "TXT_PASSARELA" "")
(command "_.layer" "m" "PINGUELA" "")
(command "_.layer" "m" "PLATAFORMA_BALANCA" "")
(command "_.layer" "m" "TXT_PLATAFORMA_BALANCA" "")
(command "_.layer" "m" "PONTE_PONTILHAO" "")
(command "_.layer" "m" "TXT_PONTE_PONTILHAO" "")
(command "_.layer" "m" "TUNEL_TRINCHEIRA" "")
(command "_.layer" "m" "TXT_TUNEL_TRINCHEIRA" "")
(command "_.layer" "m" "VIADUTO" "")
(command "_.layer" "m" "TXT_VIADUTO" "")
(command "_.layer" "m" "BUEIRO" "")
(command "_.layer" "m" "MONUMENTOS" "")
(command "_.layer" "m" "TXT_BARRAGEM_CONCRETO" "")
(command "_.layer" "m" "TXT_BARRAGEM_TERRA" "")
(command "_.layer" "m" "TXT_BUEIRO" "")
(command "_.layer" "m" "TXT_DIQUE" "")
(command "_.layer" "m" "TXT_MONUMENTOS" "")
(command "_.layer" "m" "TXT_PINGUELA" "")
(command "_.layer" "m" "MATA_BURRO" "")
(command "_.layer" "m" "CANALETA" "")
(command "_.layer" "m" "TXT_CANALETA" "")
(command "_.layer" "m" "ENCANAMENTO_ADUTORA" "")
(command "_.layer" "m" "TXT_ENCANAMENTO_ADUTORA" "")
(command "_.layer" "m" "LINHA_TRANSMISAO" "")
(command "_.layer" "m" "TXT_LINHA_TRANSMISAO" "")
(command "_.layer" "m" "SUBESTACAO" "")
(command "_.layer" "m" "TXT_SUBESTACAO" "")
(command "_.layer" "m" "REDE_AGUAS_PLUVIAIS" "")
(command "_.layer" "m" "TXT_REDE_AGUA_PLUVIAL" "")
(command "_.layer" "m" "REDE_ESGOTO" "")
(command "_.layer" "m" "TXT_REDE_ESGOTO" "")
(command "_.layer" "m" "REDE_ELETRICA" "")
(command "_.layer" "m" "TXT_REDE_ELETRICA" "")
(command "_.layer" "m" "ASPERSOR" "")
(command "_.layer" "m" "CAIXA_INSPECAO_ENERGIA" "")
(command "_.layer" "m" "CAIXA_INSPECAO_ESGOTO" "")
(command "_.layer" "m" "CAIXA_INSP_N_IDENTIFICADA" "")
(command "_.layer" "m" "CAIXA_INSPECAO_TELEFONE" "")
(command "_.layer" "m" "HIDRANTE" "")
(command "_.layer" "m" "LUMINARIA" "")
(command "_.layer" "m" "PV_DE_AGUA_PLUVIAL" "")
(command "_.layer" "m" "PV_DE_ELETRICIDADE" "")
(command "_.layer" "m" "PV_DE_ESGOTO" "")
(command "_.layer" "m" "PV_NAO_IDENTIFICADO" "")
(command "_.layer" "m" "PV_DE_TELEFONE" "")
(command "_.layer" "m" "POSTE_FERRO" "")
(command "_.layer" "m" "POSTE_MADEIRA" "")
(command "_.layer" "m" "REFLETOR" "")
(command "_.layer" "m" "TXT_CAIXA_INSPECAO_ENERGIA" "")
(command "_.layer" "m" "TXT_CAIXA_AGUA" "")
(command "_.layer" "m" "TXT_CAIXA_FORCA" "")
(command "_.layer" "m" "TXT_CAIXA_INSPECAO_AGUAPLUVIAL" "")
(command "_.layer" "m" "TXT_BOCA_LOBO" "")
(command "_.layer" "m" "TXT_CAIXA_INSPECAO_ESGOTO" "")
(command "_.layer" "m" "TXT_BOMBA_AGUA_COMBUSTIVEL" "")
(command "_.layer" "m" "TXT_CAIXA_INSPECAO_TELEFONE" "")
(command "_.layer" "m" "TXT_CAIXA_INSP_N_IDENTIFICADA" "")
(command "_.layer" "m" "TXT_GRELHA" "")
(command "_.layer" "m" "TXT_HIDRANTE" "")
(command "_.layer" "m" "TXT_PV_DE_ELETRICIDADE" "")
(command "_.layer" "m" "TXT_LUMINARIA" "")
(command "_.layer" "m" "TXT_PV_DE_AGUA_PLUVIAL" "")
(command "_.layer" "m" "TXT_POSTE_MADEIRA" "")
(command "_.layer" "m" "TXT_POSTE_CONCRETO" "")
(command "_.layer" "m" "TXT_POSTE_FERRO" "")
(command "_.layer" "m" "TXT_PV_DE_ESGOTO" "")
(command "_.layer" "m" "TXT_PV_DE_TELEFONE" "")
(command "_.layer" "m" "TXT_PV_NAO_IDENTIFICADO" "")
(command "_.layer" "m" "TXT_REFLETOR" "")
(command "_.layer" "m" "TXT_REGISTRO_DE_AGUA" "")
(command "_.layer" "m" "TXT_TORRE_TELECOMUNICACAO" "")
(command "_.layer" "m" "TXT_ANTENA" "")
(command "_.layer" "m" "POSTE_CONCRETO" "")
(command "_.layer" "m" "TORRE_TELECOMUNICACAO" "")
(command "_.layer" "m" "TORRE_TRANSMISSAO" "")
(command "_.layer" "m" "ANTENA" "")
(command "_.layer" "m" "BOCA_LOBO" "")
(command "_.layer" "m" "CAIXA_AGUA" "")
(command "_.layer" "m" "CAIXA_FORCA" "")
(command "_.layer" "m" "BOMBA_AGUA_COMBUSTIVEL" "")
(command "_.layer" "m" "CAIXA_INSPECAO_AGUAPLUVIAL" "")
(command "_.layer" "m" "GRELHA" "")
(command "_.layer" "m" "REGISTRO_DE_AGUA" "")
(command "_.layer" "m" "TXT_ASPERSOR" "")
(command "_.layer" "m" "AFLORAMENTO_ROCHOSOS" "")
(command "_.layer" "m" "TXT_AFLORAMENTO_ROCHOSOS" "")
(command "_.layer" "m" "AREIA_DUNA" "")
(command "_.layer" "m" "TXT_AREIA_DUNA" "")
(command "_.layer" "m" "ATERRO_SANITARIO" "")
(command "_.layer" "m" "TXT_ATERRO_SANITARIO" "")
(command "_.layer" "m" "BOLSAO_AGUA" "")
(command "_.layer" "m" "TXT_BOLSAO_AGUA" "")
(command "_.layer" "m" "EROSAO" "")
(command "_.layer" "m" "TXT_EROSAO" "")
(command "_.layer" "m" "MOVIMENTO_TERRA" "")
(command "_.layer" "m" "TXT_MOVIMENTO_TERRA" "")
(command "_.layer" "m" "PEDREIRA" "")
(command "_.layer" "m" "TXT_PEDREIRA" "")
(command "_.layer" "m" "BARRANCO_TALUDE" "")
(command "_.layer" "m" "TXT_BARRANCO_TALUDE" "")
(command "_.layer" "m" "VEG_BAIXO_PORTE" "")
(command "_.layer" "m" "TXT_VEG_BAIXO_PORTE" "")
(command "_.layer" "m" "VEG_MEDIO_PORTE" "")
(command "_.layer" "m" "TXT_VEG_MEDIO_PORTE" "")
(command "_.layer" "m" "VEG_GRANDE_PORTE" "")
(command "_.layer" "m" "TXT_VEG_GRANDE_PORTE" "")
(command "_.layer" "m" "ESTUFA" "")
(command "_.layer" "m" "TXT_ESTUFA" "")
(command "_.layer" "m" "ARVORE" "")
(command "_.layer" "m" "COQUEIRO_PALMEIRA" "")
(command "_.layer" "m" "TXT_CERRADO" "")
(command "_.layer" "m" "TXT_COQUEIRO_PALMEIRA" "")
(command "_.layer" "m" "TXT_RELORESTAMENTO" "")
(command "_.layer" "m" "RELORESTAMENTO" "")
(command "_.layer" "m" "TXT_ARVORE" "")
(command "_.layer" "m" "CALCADA" "")
(command "_.layer" "m" "TXT_FERROVIA_BITOLA_SIMPLES" "")
(command "_.layer" "m" "HELIPORTO" "")
(command "_.layer" "m" "TXT_HELIPORTO" "")
(command "_.layer" "m" "MEIO_FIO_COM_PAVIMENTACAO" "")
(command "_.layer" "m" "TXT_MEIO_FIO_COM_PAVIMENTACAO" "")
(command "_.layer" "m" "MEIO_FIO_SEM_PAVIMENTACAO" "")
(command "_.layer" "m" "TXT_MEIO_FIO_SEM_PAVIMENTACAO" "")
(command "_.layer" "m" "CAMPO_POUSO" "")
(command "_.layer" "m" "TXT_METROVIA" "")
(command "_.layer" "m" "PISTA_BICICROS_MOTOCROS" "")
(command "_.layer" "m" "ACOSTAMENTO" "")
(command "_.layer" "m" "AEROPORTO" "")
(command "_.layer" "m" "TXT_AEROPORTO" "")
(command "_.layer" "m" "AUTODROMO_KARTODROMO" "")
(command "_.layer" "m" "TXT_AUTODROMO_KARTODROMO" "")
(command "_.layer" "m" "TXT_CAMPO_POUSO" "")
(command "_.layer" "m" "CICLOVIA" "")
(command "_.layer" "m" "TXT_CICLOVIA" "")
(command "_.layer" "m" "TXT_PISTA_BICICROS_MOTOCROS" "")
(command "_.layer" "m" "TXT_VIA_CONSTRUCAO" "")
(command "_.layer" "m" "VIA_NAO_PAVIEMENTADA" "")
(command "_.layer" "m" "VIA_PAV_ASFALTO" "")
(command "_.layer" "m" "TXT_VIA_PAV_ASFALTO" "")
(command "_.layer" "m" "VIA_PAV_BLOQUETE" "")
(command "_.layer" "m" "TXT_VIA_PAV_BLOQUETE" "")
(command "_.layer" "m" "VIA_PAV_PEDRA" "")
(command "_.layer" "m" "TXT_VIA_PAV_PEDRA" "")
(command "_.layer" "m" "FERROVIA_BITOLA_SIMPLES" "")
(command "_.layer" "m" "FERROVIA_BITOLA_DUPLA" "")
(command "_.layer" "m" "EIXO_PISTA" "")
(command "_.layer" "m" "VIA_CONSTRUCAO" "")
(command "_.layer" "m" "METROVIA" "")
(command "_.layer" "m" "CAMINHO_TRILHA" "")
(command "_.layer" "m" "HELIPONTO" "")
(command "_.layer" "m" "TXT_CALCADA" "")
(command "_.layer" "m" "TXT_CAMINHO_TRILHA" "")
(command "_.layer" "m" "TXT_FERROVIA_BITOLA_DUPLA" "")
(command "_.layer" "m" "TXT_EIXO_PISTA" "")
(command "_.layer" "m" "TXT_VIA_NAO_PAVIEMENTADA" "")
(command "_.layer" "m" "TXT_HELIPONTO" "")
(command "_.layer" "m" "AREA_LAZER" "")
(command "_.layer" "m" "TXT_AREA_LAZER" "")
(command "_.layer" "m" "TXT_SETOR" "")
(command "_.layer" "m" "CAMPO_FUTEBOL" "")
(command "_.layer" "m" "TXT_CAMPO_FUTEBOL" "")
(command "_.layer" "m" "CANTEIRO_JARDIM" "")
(command "_.layer" "m" "TXT_CANTEIRO_JARDIM" "")
(command "_.layer" "m" "QUADESPORTE" "")
(command "_.layer" "m" "TXT_QUADESPORTE" "")
(command "_.layer" "m" "TXT_LOCALIDADE" "")
(command "_.layer" "m" "RN_OFICIAL" "")
(command "_.layer" "m" "RN_IMPLANTADO" "")
(command "_.layer" "m" "VERTICE_OFICIAL" "")
(command "_.layer" "m" "VERTICE_IMPLANTADO" "")
(command "_.layer" "m" "APOIO_FOTOGRAMETRICO" "")
(command "_.layer" "m" "COTA_DE_APARELHO" "")
(command "_.layer" "m" "COTA_DE_CAMPO" "")
(command "_.layer" "m" "TXT_COTA_PONTO_POL_SEC" "")
(command "_.layer" "m" "TXT_DESCRICAO_PONTO_POL_PPAL" "")
(command "_.layer" "m" "TXT_COTA_DE_APARELHO" "")
(command "_.layer" "m" "TXT_COTA_DE_CAMPO" "")
(command "_.layer" "m" "TXT_COTA_PONTO_POL_PPAL" "")
(command "_.layer" "m" "TXT_DESCRICAO_PONTO_POL_SEC" "")
(command "_.layer" "m" "TXT_FURO_DE_SONDAGEM" "")
(command "_.layer" "m" "TXT_NOME_PONTO_POL_PPAL" "")
(command "_.layer" "m" "TXT_NOME_PONTO_POL_SEC" "")
(command "_.layer" "m" "TXT_VERTICE_IMPLANTADO" "")
(command "_.layer" "m" "TXT_RN_IMPLANTADO" "")
(command "_.layer" "m" "TXT_RN_OFICIAL" "")
(command "_.layer" "m" "TXT_PONTO_AUXILIAR" "")
(command "_.layer" "m" "TXT_VERTICE_OFICIAL" "")
(command "_.layer" "m" "TXT_AZIMUTE" "")
(command "_.layer" "m" "TXT_APOIO_FOTOGRAMETRICO" "")
(command "_.layer" "m" "FURO_DE_SONDAGEM" "")
(command "_.layer" "m" "POLIGONAL_PRINCIPAL" "")
(command "_.layer" "m" "POLIGONAL_SECUNDARIA" "")
(command "_.layer" "m" "PONTO_AUXILIAR" "")
(command "_.layer" "m" "TXT_EST_ROD_FERR_METROV" "")
(command "_.layer" "m" "TXT_ESTACIONAMENTO" "")
(command "_.layer" "m" "TANQUE" "")
(command "_.layer" "m" "EST_ROD_FERR_METROV" "")
(command "_.layer" "m" "TXT_EDIFICACAO" "")
(command "_.layer" "m" "TXT_CEMITERIO" "")
(command "_.layer" "m" "CEMITERIO" "")
(command "_.layer" "m" "EDIFICACAO" "")
(command "_.layer" "m" "TXT_PILAR" "")
(command "_.layer" "m" "TXT_PISCINA" "")
(command "_.layer" "m" "TXT_RESERVATORIO" "")
(command "_.layer" "m" "TXT_RUINA" "")
(command "_.layer" "m" "ESTACIONAMENTO" "")
(command "_.layer" "m" "RESERVATORIO" "")
(command "_.layer" "m" "PISCINA" "")
(command "_.layer" "m" "TXT_TANQUE" "")
(command "_.layer" "m" "RUINA" "")
(command "_.layer" "m" "PROJECAO_TELHADO" "")
(command "_.layer" "m" "PILAR" "")
(command "_.layer" "m" "TXT_DIMENSOES" "")
(command "_.layer" "m" "TXT_COORD_AREA" "")
(command "_.layer" "m" "TXT_PLAN_AZIMUTE_DISTANCIA" "")
(command "_.layer" "m" "DIMENSOES" "")
(command "_.layer" "m" "PLAN_AZIMUTE_DISTANCIA" "")
(command "_.layer" "m" "TXT_MALHAGEO" "")
(command "_.layer" "m" "TXT_MALHAUTM" "")
(command "_.layer" "m" "MALHAGEO" "")
(command "_.layer" "m" "MALHAUTM" "")
(command "_.layer" "m" "NORTE" "")
(setq Tabela_Base
   (list
         (list "SOLEIRA" 12 "CONTINUOUS" "yes")
         (list "GERATRIZ" 12 "CONTINUOUS" "yes")
         (list "CURVA_INTERMEDIARIA" 8 "CONTINUOUS" "yes")
         (list "CURVA_MESTRA" 9 "CONTINUOUS" "yes")
         (list "TXT_CURVA_MESTRA" 24 "CONTINUOUS" "yes")
         (list "TXT_CURVA_INTERMEDIARIA" 24 "CONTINUOUS" "yes")
         (list "TXT_GERATRIZ" 24 "CONTINUOUS" "yes")
         (list "TXT_SOLEIRA" 24 "CONTINUOUS" "yes")
         (list "LIMITE_DISTRITAL" 13 "LIM_DISTRITAL" "yes")
         (list "TXT_LIMITE_DISTRITAL" 33 "CONTINUOUS" "yes")
         (list "TXT_LIMITE_POLIGONAL" 33 "CONTINUOUS" "yes")
         (list "LIMITE_ESTADUAL" 13 "CONTINUOUS" "yes")
         (list "TXT_LIMITE_ESTADUAL" 33 "CONTINUOUS" "yes")
         (list "LIMITE_INTERNACIONAL" 15 "LIM_INTERNACIONAL" "yes")
         (list "TXT_LIMITE_INTERNACIONAL" 33 "CONTINUOUS" "yes")
         (list "LIMITE_MUNICIPAL" 12 "LIM_MUNICIPAL" "yes")
         (list "TXT_LIMITE_MUNICIPAL" 33 "CONTINUOUS" "yes")
         (list "PERIMETRO_URBANO" 14 "LIM_PERURBANO" "yes")
         (list "TXT_PERIMETRO_URBANO" 33 "CONTINUOUS" "yes")
         (list "POLIGONAL_DE_ESTUDO" 210 "CONTINUOUS" "yes")
         (list "TXT_POLIGONAL_DE_ESTUDO" 33 "CONTINUOUS" "yes")
         (list "LIMITE_DE_PROPRIEDADE" 13 "CONTINUOUS" "yes")
         (list "TXT_LIMITE_PROPRIEDADE" 33 "CONTINUOUS" "yes")
         (list "TXT_LIMITE_BAIRRO" 33 "CONTINUOUS" "yes")
         (list "TXT_LIMITE_QUADRA" 33 "CONTINUOUS" "yes")
         (list "TXT_LIMITE_SETOR" 33 "CONTINUOUS" "yes")
         (list "LIMITE_BAIRRO" 12 "LIM_BAIRRO" "yes")
         (list "LIMITE_POLIGONAL" 13 "CONTINUOUS" "yes")
         (list "LIMITE_QUADRA" 13 "CONTINUOUS" "yes")
         (list "LIMITE_SETOR" 12 "LIM_SETOR" "yes")
         (list "ALAMBRADO_GRADE" 28 "ALAMB_GRADE" "yes")
         (list "CERCA_ARAME" 18 "CERCA_ARAME" "yes")
         (list "CERCA_MADEIRA" 42 "CERCA_MADEIRA" "yes")
         (list "CERCA_MISTA" 32 "CERCA_MISTA" "yes")
         (list "CERCA_VIVA" 94 "CERCA_VIVA" "yes")
         (list "MURO" 21 "CONTINUOUS" "yes")
         (list "LOTE_TOPOGRAFICO" 12 "CONTINUOUS" "yes")
         (list "TXT_LOTE_TOPOGRAFICO" 24 "CONTINUOUS" "yes")
         (list "PORTAO" 12 "CONTINUOUS" "yes")
         (list "MURETA" 132 "CONTINUOUS" "yes")
         (list "TXT_MURETA" 24 "CONTINUOUS" "yes")
         (list "TAPUME" 12 "CONTINUOUS" "yes")
         (list "ALAGADO" 151 "CONTINUOUS" "yes")
         (list "BREJO" 141 "CONTINUOUS" "yes")
         (list "CACHOEIRA" 160 "CACHOEIRA" "yes")
         (list "CANAL" 12 "CONTINUOUS" "yes")
         (list "TXT_CANAL" 24 "CONTINUOUS" "yes")
         (list "CORREDEIRA" 180 "CONTINUOUS" "yes")
         (list "RIO_COR_INTERMITENTE" 150 "RIO_COR_INTERM" "yes")
         (list "TXT_RIO_COR_INTERMITENTE" 33 "CONTINUOUS" "yes")
         (list "RIO_COR_PERENE" 170 "CONTINUOUS" "yes")
         (list "TXT_RIO_COR_PERENE" 33 "CONTINUOUS" "yes")
         (list "LAGO_LAGOA_INTERMITENTE" 172 "HIDDEN" "yes")
         (list "TXT_LAGO_LAGOA_INTERMITENTE" 33 "CONTINUOUS" "yes")
         (list "LAGO_LAGOA_PERENE" 160 "CONTINUOUS" "yes")
         (list "TXT_LAGO_LAGOA_PERENE" 33 "CONTINUOUS" "yes")
         (list "VALA" 35 "VALA" "yes")
         (list "FONTE_NASCENTE" 161 "CONTINUOUS" "yes")
         (list "TXT_ALAGADO" 24 "CONTINUOUS" "yes")
         (list "TXT_BREJO" 24 "CONTINUOUS" "yes")
         (list "TXT_CACHOEIRA" 24 "CONTINUOUS" "yes")
         (list "TXT_CORREDEIRA" 24 "CONTINUOUS" "yes")
         (list "TXT_FONTE_NASCENTE" 24 "CONTINUOUS" "yes")
         (list "TXT_GROTA" 24 "CONTINUOUS" "yes")
         (list "TXT_POCO" 24 "CONTINUOUS" "yes")
         (list "TXT_VALA" 24 "CONTINUOUS" "yes")
         (list "GROTA" 34 "CONTINUOUS" "yes")
         (list "POCO" 140 "CONTINUOUS" "yes")
         (list "CAIXA_CORREIO" 24 "CONTINUOUS" "yes")
         (list "LIXEIRA" 24 "CONTINUOUS" "yes")
         (list "QUIOSQUE" 24 "CONTINUOUS" "yes")
         (list "SEMAFORO" 33 "CONTINUOUS" "yes")
         (list "TELEFONE_PUBLICO" 24 "CONTINUOUS" "yes")
         (list "TELEFONE_PUBLICO_CABINE" 24 "CONTINUOUS" "yes")
         (list "TXT_BANCO" 24 "CONTINUOUS" "yes")
         (list "TXT_LIXEIRA" 24 "CONTINUOUS" "yes")
         (list "TXT_PLACA_SINALIZACAO" 24 "CONTINUOUS" "yes")
         (list "TXT_PONTO_ONIBUS" 24 "CONTINUOUS" "yes")
         (list "TXT_PONTO_TAXI" 24 "CONTINUOUS" "yes")
         (list "TXT_PLACA_PROPAGANDA" 24 "CONTINUOUS" "yes")
         (list "TXT_QUIOSQUE" 24 "CONTINUOUS" "yes")
         (list "TXT_SEMAFORO" 24 "CONTINUOUS" "yes")
         (list "TXT_TELEFONE_PUBLICO" 24 "CONTINUOUS" "yes")
         (list "TXT_TELEFONE_PUBLICO_CABINE" 24 "CONTINUOUS" "yes")
         (list "TXT_BANCA_REVISTA" 24 "CONTINUOUS" "yes")
         (list "BANCA_REVISTA" 24 "CONTINUOUS" "yes")
         (list "BANCO" 24 "CONTINUOUS" "yes")
         (list "PLACA_SINALIZACAO" 24 "CONTINUOUS" "yes")
         (list "PLACA_PROPAGANDA" 24 "CONTINUOUS" "yes")
         (list "PONTO_ONIBUS" 24 "CONTINUOUS" "yes")
         (list "PONTO_TAXI" 33 "CONTINUOUS" "yes")
         (list "TXT_CAIXA_CORREIO" 24 "CONTINUOUS" "yes")
         (list "ARQUIBANCADA" 12 "CONTINUOUS" "yes")
         (list "TXT_ARQUIBANCADA" 24 "CONTINUOUS" "yes")
         (list "BARRAGEM_CONCRETO" 160 "BARRAGEM_CONC" "yes")
         (list "BARRAGEM_TERRA" 160 "BARRAGEM_TERR" "yes")
         (list "DIQUE" 12 "DIQUE" "yes")
         (list "ESCADARIA_RAMPA" 12 "CONTINUOUS" "yes")
         (list "TXT_ESCADARIA_RAMPA" 24 "CONTINUOUS" "yes")
         (list "GUARD_RAIL" 12 "GUARD_RAIL" "yes")
         (list "MURO_ARRIMO" 130 "MURO_ARRIMO" "yes")
         (list "TXT_MURO_ARRIMO" 24 "CONTINUOUS" "yes")
         (list "PASSAGEM_SUBTERRANEA" 12 "PASS_SUBTE" "yes")
         (list "TXT_PASSAGEM_SUBTERRANEA" 24 "CONTINUOUS" "yes")
         (list "PASSARELA" 12 "CONTINUOUS" "yes")
         (list "TXT_PASSARELA" 24 "CONTINUOUS" "yes")
         (list "PINGUELA" 13 "CONTINUOUS" "yes")
         (list "PLATAFORMA_BALANCA" 12 "CONTINUOUS" "yes")
         (list "TXT_PLATAFORMA_BALANCA" 24 "CONTINUOUS" "yes")
         (list "PONTE_PONTILHAO" 221 "CONTINUOUS" "yes")
         (list "TXT_PONTE_PONTILHAO" 24 "CONTINUOUS" "yes")
         (list "TUNEL_TRINCHEIRA" 14 "TUNEL" "yes")
         (list "TXT_TUNEL_TRINCHEIRA" 24 "CONTINUOUS" "yes")
         (list "VIADUTO" 221 "CONTINUOUS" "yes")
         (list "TXT_VIADUTO" 24 "CONTINUOUS" "yes")
         (list "BUEIRO" 33 "CONTINUOUS" "yes")
         (list "MONUMENTOS" 13 "CONTINUOUS" "yes")
         (list "TXT_BARRAGEM_CONCRETO" 24 "CONTINUOUS" "yes")
         (list "TXT_BARRAGEM_TERRA" 24 "CONTINUOUS" "yes")
         (list "TXT_BUEIRO" 24 "CONTINUOUS" "yes")
         (list "TXT_DIQUE" 24 "CONTINUOUS" "yes")
         (list "TXT_MONUMENTOS" 24 "CONTINUOUS" "yes")
         (list "TXT_PINGUELA" 24 "CONTINUOUS" "yes")
         (list "MATA_BURRO" 33 "CONTINUOUS" "yes")
         (list "CANALETA" 31 "CONTINUOUS" "yes")
         (list "TXT_CANALETA" 24 "CONTINUOUS" "yes")
         (list "ENCANAMENTO_ADUTORA" 33 "ADUTORA" "yes")
         (list "TXT_ENCANAMENTO_ADUTORA" 24 "CONTINUOUS" "yes")
         (list "LINHA_TRANSMISAO" 12 "LINHA_TRANS" "yes")
         (list "TXT_LINHA_TRANSMISAO" 24 "CONTINUOUS" "yes")
         (list "SUBESTACAO" 12 "CONTINUOUS" "yes")
         (list "TXT_SUBESTACAO" 24 "CONTINUOUS" "yes")
         (list "REDE_AGUAS_PLUVIAIS" 14 "CONTINUOUS" "yes")
         (list "TXT_REDE_AGUA_PLUVIAL" 24 "CONTINUOUS" "yes")
         (list "REDE_ESGOTO" 14 "REDE_ESGOTO" "yes")
         (list "TXT_REDE_ESGOTO" 24 "CONTINUOUS" "yes")
         (list "REDE_ELETRICA" 25 "REDE_ELET" "yes")
         (list "TXT_REDE_ELETRICA" 24 "CONTINUOUS" "yes")
         (list "ASPERSOR" 24 "CONTINUOUS" "yes")
         (list "CAIXA_INSPECAO_ENERGIA" 33 "CONTINUOUS" "yes")
         (list "CAIXA_INSPECAO_ESGOTO" 33 "CONTINUOUS" "yes")
         (list "CAIXA_INSP_N_IDENTIFICADA" 33 "CONTINUOUS" "yes")
         (list "CAIXA_INSPECAO_TELEFONE" 33 "CONTINUOUS" "yes")
         (list "HIDRANTE" 24 "CONTINUOUS" "yes")
         (list "LUMINARIA" 33 "CONTINUOUS" "yes")
         (list "PV_DE_AGUA_PLUVIAL" 33 "CONTINUOUS" "yes")
         (list "PV_DE_ELETRICIDADE" 33 "CONTINUOUS" "yes")
         (list "PV_DE_ESGOTO" 33 "CONTINUOUS" "yes")
         (list "PV_NAO_IDENTIFICADO" 33 "CONTINUOUS" "yes")
         (list "PV_DE_TELEFONE" 33 "CONTINUOUS" "yes")
         (list "POSTE_FERRO" 33 "CONTINUOUS" "yes")
         (list "POSTE_MADEIRA" 33 "CONTINUOUS" "yes")
         (list "REFLETOR" 33 "CONTINUOUS" "yes")
         (list "TXT_CAIXA_INSPECAO_ENERGIA" 24 "CONTINUOUS" "yes")
         (list "TXT_CAIXA_AGUA" 24 "CONTINUOUS" "yes")
         (list "TXT_CAIXA_FORCA" 24 "CONTINUOUS" "yes")
         (list "TXT_CAIXA_INSPECAO_AGUAPLUVIAL" 24 "CONTINUOUS" "yes")
         (list "TXT_BOCA_LOBO" 24 "CONTINUOUS" "yes")
         (list "TXT_CAIXA_INSPECAO_ESGOTO" 24 "CONTINUOUS" "yes")
         (list "TXT_BOMBA_AGUA_COMBUSTIVEL" 24 "CONTINUOUS" "yes")
         (list "TXT_CAIXA_INSPECAO_TELEFONE" 24 "CONTINUOUS" "yes")
         (list "TXT_CAIXA_INSP_N_IDENTIFICADA" 24 "CONTINUOUS" "yes")
         (list "TXT_GRELHA" 24 "CONTINUOUS" "yes")
         (list "TXT_HIDRANTE" 24 "CONTINUOUS" "yes")
         (list "TXT_PV_DE_ELETRICIDADE" 24 "CONTINUOUS" "yes")
         (list "TXT_LUMINARIA" 24 "CONTINUOUS" "yes")
         (list "TXT_PV_DE_AGUA_PLUVIAL" 24 "CONTINUOUS" "yes")
         (list "TXT_POSTE_MADEIRA" 24 "CONTINUOUS" "yes")
         (list "TXT_POSTE_CONCRETO" 24 "CONTINUOUS" "yes")
         (list "TXT_POSTE_FERRO" 24 "CONTINUOUS" "yes")
         (list "TXT_PV_DE_ESGOTO" 24 "CONTINUOUS" "yes")
         (list "TXT_PV_DE_TELEFONE" 24 "CONTINUOUS" "yes")
         (list "TXT_PV_NAO_IDENTIFICADO" 24 "CONTINUOUS" "yes")
         (list "TXT_REFLETOR" 24 "CONTINUOUS" "yes")
         (list "TXT_REGISTRO_DE_AGUA" 24 "CONTINUOUS" "yes")
         (list "TXT_TORRE_TELECOMUNICACAO" 24 "CONTINUOUS" "yes")
         (list "TXT_ANTENA" 24 "CONTINUOUS" "yes")
         (list "POSTE_CONCRETO" 33 "CONTINUOUS" "yes")
         (list "TORRE_TELECOMUNICACAO" 24 "CONTINUOUS" "yes")
         (list "TORRE_TRANSMISSAO" 33 "CONTINUOUS" "yes")
         (list "ANTENA" 33 "CONTINUOUS" "yes")
         (list "BOCA_LOBO" 32 "CONTINUOUS" "yes")
         (list "CAIXA_AGUA" 140 "CONTINUOUS" "yes")
         (list "CAIXA_FORCA" 33 "CONTINUOUS" "yes")
         (list "BOMBA_AGUA_COMBUSTIVEL" 24 "CONTINUOUS" "yes")
         (list "CAIXA_INSPECAO_AGUAPLUVIAL" 33 "CONTINUOUS" "yes")
         (list "GRELHA" 24 "GRELHA" "yes")
         (list "REGISTRO_DE_AGUA" 33 "CONTINUOUS" "yes")
         (list "TXT_ASPERSOR" 24 "CONTINUOUS" "yes")
         (list "AFLORAMENTO_ROCHOSOS" 12 "LIXOMOVTERRA" "yes")
         (list "TXT_AFLORAMENTO_ROCHOSOS" 24 "CONTINUOUS" "yes")
         (list "AREIA_DUNA" 12 "LIXOMOVTERRA" "yes")
         (list "TXT_AREIA_DUNA" 24 "CONTINUOUS" "yes")
         (list "ATERRO_SANITARIO" 12 "LIXOMOVTERRA" "yes")
         (list "TXT_ATERRO_SANITARIO" 33 "CONTINUOUS" "yes")
         (list "BOLSAO_AGUA" 141 "CONTINUOUS" "yes")
         (list "TXT_BOLSAO_AGUA" 33 "CONTINUOUS" "yes")
         (list "EROSAO" 12 "LIXOMOVTERRA" "yes")
         (list "TXT_EROSAO" 24 "CONTINUOUS" "yes")
         (list "MOVIMENTO_TERRA" 12 "LIXOMOVTERRA" "yes")
         (list "TXT_MOVIMENTO_TERRA" 24 "CONTINUOUS" "yes")
         (list "PEDREIRA" 12 "LIXOMOVTERRA" "yes")
         (list "TXT_PEDREIRA" 24 "CONTINUOUS" "yes")
         (list "BARRANCO_TALUDE" 21 "CONTINUOUS" "yes")
         (list "TXT_BARRANCO_TALUDE" 24 "CONTINUOUS" "yes")
         (list "VEG_BAIXO_PORTE" 90 "VEGETACAO" "yes")
         (list "TXT_VEG_BAIXO_PORTE" 33 "CONTINUOUS" "yes")
         (list "VEG_MEDIO_PORTE" 90 "VEGETACAO" "yes")
         (list "TXT_VEG_MEDIO_PORTE" 33 "CONTINUOUS" "yes")
         (list "VEG_GRANDE_PORTE" 90 "VEGETACAO" "yes")
         (list "TXT_VEG_GRANDE_PORTE" 33 "CONTINUOUS" "yes")
         (list "ESTUFA" 12 "CONTINUOUS" "yes")
         (list "TXT_ESTUFA" 24 "CONTINUOUS" "yes")
         (list "ARVORE" 80 "CONTINUOUS" "yes")
         (list "COQUEIRO_PALMEIRA" 90 "CONTINUOUS" "yes")
         (list "TXT_CERRADO" 33 "CONTINUOUS" "yes")
         (list "TXT_COQUEIRO_PALMEIRA" 24 "CONTINUOUS" "yes")
         (list "TXT_RELORESTAMENTO" 33 "CONTINUOUS" "yes")
         (list "RELORESTAMENTO" 90 "VEGETACAO" "yes")
         (list "TXT_ARVORE" 24 "CONTINUOUS" "yes")
         (list "CALCADA" 21 "CONTINUOUS" "yes")
         (list "TXT_FERROVIA_BITOLA_SIMPLES" 24 "CONTINUOUS" "yes")
         (list "HELIPORTO" 12 "CONTINUOUS" "yes")
         (list "TXT_HELIPORTO" 33 "CONTINUOUS" "yes")
         (list "MEIO_FIO_COM_PAVIMENTACAO" 220 "CONTINUOUS" "yes")
         (list "TXT_MEIO_FIO_COM_PAVIMENTACAO" 24 "CONTINUOUS" "yes")
         (list "MEIO_FIO_SEM_PAVIMENTACAO" 220 "CONTINUOUS" "yes")
         (list "TXT_MEIO_FIO_SEM_PAVIMENTACAO" 24 "CONTINUOUS" "yes")
         (list "CAMPO_POUSO" 12 "CONTINUOUS" "yes")
         (list "TXT_METROVIA" 24 "CONTINUOUS" "yes")
         (list "PISTA_BICICROS_MOTOCROS" 12 "CONTINUOUS" "yes")
         (list "ACOSTAMENTO" 242 "CONTINUOUS" "yes")
         (list "AEROPORTO" 244 "CONTINUOUS" "yes")
         (list "TXT_AEROPORTO" 33 "CONTINUOUS" "yes")
         (list "AUTODROMO_KARTODROMO" 12 "CONTINUOUS" "yes")
         (list "TXT_AUTODROMO_KARTODROMO" 33 "CONTINUOUS" "yes")
         (list "TXT_CAMPO_POUSO" 33 "CONTINUOUS" "yes")
         (list "CICLOVIA" 11 "CONTINUOUS" "yes")
         (list "TXT_CICLOVIA" 33 "CONTINUOUS" "yes")
         (list "TXT_PISTA_BICICROS_MOTOCROS" 24 "CONTINUOUS" "yes")
         (list "TXT_VIA_CONSTRUCAO" 24 "CONTINUOUS" "yes")
         (list "VIA_NAO_PAVIEMENTADA" 22 "VIANAOPAVIMENTADA" "yes")
         (list "VIA_PAV_ASFALTO" 23 "VIAPAV_ASF" "yes")
         (list "TXT_VIA_PAV_ASFALTO" 24 "CONTINUOUS" "yes")
         (list "VIA_PAV_BLOQUETE" 23 "VIAPAV_BLO" "yes")
         (list "TXT_VIA_PAV_BLOQUETE" 24 "CONTINUOUS" "yes")
         (list "VIA_PAV_PEDRA" 23 "VIAPAV_PED" "yes")
         (list "TXT_VIA_PAV_PEDRA" 24 "CONTINUOUS" "yes")
         (list "FERROVIA_BITOLA_SIMPLES" 12 "FERROVIASIMPLES" "yes")
         (list "FERROVIA_BITOLA_DUPLA" 12 "FERROVIADUPLA" "yes")
         (list "EIXO_PISTA" 21 "EIXOPISTA" "yes")
         (list "VIA_CONSTRUCAO" 220 "VIAEMCONSTRUCAO" "yes")
         (list "METROVIA" 12 "FERROVIASIMPLES" "yes")
         (list "CAMINHO_TRILHA" 12 "CAMINHOTRILHA" "yes")
         (list "HELIPONTO" 13 "CONTINUOUS" "yes")
         (list "TXT_CALCADA" 33 "CONTINUOUS" "yes")
         (list "TXT_CAMINHO_TRILHA" 33 "CONTINUOUS" "yes")
         (list "TXT_FERROVIA_BITOLA_DUPLA" 24 "CONTINUOUS" "yes")
         (list "TXT_EIXO_PISTA" 33 "CONTINUOUS" "yes")
         (list "TXT_VIA_NAO_PAVIEMENTADA" 24 "CONTINUOUS" "yes")
         (list "TXT_HELIPONTO" 33 "CONTINUOUS" "yes")
         (list "AREA_LAZER" 12 "CONTINUOUS" "yes")
         (list "TXT_AREA_LAZER" 24 "CONTINUOUS" "yes")
         (list "TXT_SETOR" 35 "CONTINUOUS" "yes")
         (list "CAMPO_FUTEBOL" 126 "CONTINUOUS" "yes")
         (list "TXT_CAMPO_FUTEBOL" 24 "CONTINUOUS" "yes")
         (list "CANTEIRO_JARDIM" 12 "CONTINUOUS" "yes")
         (list "TXT_CANTEIRO_JARDIM" 24 "CONTINUOUS" "yes")
         (list "QUADESPORTE" 126 "CONTINUOUS" "yes")
         (list "TXT_QUADESPORTE" 24 "CONTINUOUS" "yes")
         (list "TXT_LOCALIDADE" 33 "CONTINUOUS" "yes")
         (list "RN_OFICIAL" 33 "CONTINUOUS" "yes")
         (list "RN_IMPLANTADO" 33 "CONTINUOUS" "yes")
         (list "VERTICE_OFICIAL" 33 "CONTINUOUS" "yes")
         (list "VERTICE_IMPLANTADO" 33 "CONTINUOUS" "yes")
         (list "APOIO_FOTOGRAMETRICO" 33 "CONTINUOUS" "yes")
         (list "COTA_DE_APARELHO" 33 "CONTINUOUS" "yes")
         (list "COTA_DE_CAMPO" 33 "CONTINUOUS" "yes")
         (list "TXT_COTA_PONTO_POL_SEC" 24 "CONTINUOUS" "yes")
         (list "TXT_DESCRICAO_PONTO_POL_PPAL" 24 "CONTINUOUS" "yes")
         (list "TXT_COTA_DE_APARELHO" 24 "CONTINUOUS" "yes")
         (list "TXT_COTA_DE_CAMPO" 24 "CONTINUOUS" "yes")
         (list "TXT_COTA_PONTO_POL_PPAL" 24 "CONTINUOUS" "yes")
         (list "TXT_DESCRICAO_PONTO_POL_SEC" 24 "CONTINUOUS" "yes")
         (list "TXT_FURO_DE_SONDAGEM" 24 "CONTINUOUS" "yes")
         (list "TXT_NOME_PONTO_POL_PPAL" 24 "CONTINUOUS" "yes")
         (list "TXT_NOME_PONTO_POL_SEC" 24 "CONTINUOUS" "yes")
         (list "TXT_VERTICE_IMPLANTADO" 24 "CONTINUOUS" "yes")
         (list "TXT_RN_IMPLANTADO" 24 "CONTINUOUS" "yes")
         (list "TXT_RN_OFICIAL" 24 "CONTINUOUS" "yes")
         (list "TXT_PONTO_AUXILIAR" 24 "CONTINUOUS" "yes")
         (list "TXT_VERTICE_OFICIAL" 24 "CONTINUOUS" "yes")
         (list "TXT_AZIMUTE" 24 "CONTINUOUS" "yes")
         (list "TXT_APOIO_FOTOGRAMETRICO" 24 "CONTINUOUS" "yes")
         (list "FURO_DE_SONDAGEM" 33 "CONTINUOUS" "yes")
         (list "POLIGONAL_PRINCIPAL" 33 "CONTINUOUS" "yes")
         (list "POLIGONAL_SECUNDARIA" 33 "CONTINUOUS" "yes")
         (list "PONTO_AUXILIAR" 24 "CONTINUOUS" "yes")
         (list "TXT_EST_ROD_FERR_METROV" 24 "CONTINUOUS" "yes")
         (list "TXT_ESTACIONAMENTO" 24 "CONTINUOUS" "yes")
         (list "TANQUE" 130 "CONTINUOUS" "yes")
         (list "EST_ROD_FERR_METROV" 204 "CONTINUOUS" "yes")
         (list "TXT_EDIFICACAO" 24 "CONTINUOUS" "yes")
         (list "TXT_CEMITERIO" 33 "CONTINUOUS" "yes")
         (list "CEMITERIO" 13 "CONTINUOUS" "yes")
         (list "EDIFICACAO" 204 "CONTINUOUS" "yes")
         (list "TXT_PILAR" 24 "CONTINUOUS" "yes")
         (list "TXT_PISCINA" 24 "CONTINUOUS" "yes")
         (list "TXT_RESERVATORIO" 24 "CONTINUOUS" "yes")
         (list "TXT_RUINA" 33 "CONTINUOUS" "yes")
         (list "ESTACIONAMENTO" 12 "CONTINUOUS" "yes")
         (list "RESERVATORIO" 130 "CONTINUOUS" "yes")
         (list "PISCINA" 130 "CONTINUOUS" "yes")
         (list "TXT_TANQUE" 24 "CONTINUOUS" "yes")
         (list "RUINA" 204 "RUINA" "yes")
         (list "PROJECAO_TELHADO" 12 "PROJECAO" "yes")
         (list "PILAR" 12 "CONTINUOUS" "yes")
         (list "TXT_DIMENSOES" 24 "CONTINUOUS" "yes")
         (list "TXT_COORD_AREA" 24 "CONTINUOUS" "yes")
         (list "TXT_PLAN_AZIMUTE_DISTANCIA" 24 "CONTINUOUS" "yes")
         (list "DIMENSOES" 24 "CONTINUOUS" "yes")
         (list "PLAN_AZIMUTE_DISTANCIA" 220 "CONTINUOUS" "yes")
         (list "TXT_MALHAGEO" 24 "CONTINUOUS" "yes")
         (list "TXT_MALHAUTM" 24 "CONTINUOUS" "yes")
         (list "MALHAGEO" 12 "CONTINUOUS" "yes")
         (list "MALHAUTM" 191 "CONTINUOUS" "yes")
         (list "NORTE" 13 "CONTINUOUS" "yes")
      );fim do list
  ); fim do setq

;*************************************************************
;*****************  Carrega traços especiais *****************
;*************************************************************  

(command "-linetype" "l" "ADUTORA" "LINHAS_2009.LIN" "")
(command "-linetype" "l" "ALAMBRADO_GRADE" "LINHAS_2009.LIN" "");;XXXXXXXXX
(command "-linetype" "l" "BARRAGEM_CONCRETO" "LINHAS_2009.LIN" "");;XXXXXXX
(command "-linetype" "l" "BARRAGEM_TERRA" "LINHAS_2009.LIN" "");;XXXXXXXXXX
(command "-linetype" "l" "CACHOEIRA" "LINHAS_2009.LIN" "");;XXXXXXXXXXXXXXX
(command "-linetype" "l" "CAMINHO_TRILHA" "LINHAS_2009.LIN" "");;XXXXXXXXXX
(command "-linetype" "l" "CERCA" "LINHAS_2009.LIN" "");;XXXXXXXXXXXXXXXXXXX
(command "-linetype" "l" "CERCA_MADEIRA1" "LINHAS_2009.LIN" "");;XXXXXXXXXX
(command "-linetype" "l" "CERCA_MISTA1" "LINHAS_2009.LIN" "");;XXXXXXXXXXXX
(command "-linetype" "l" "CERCA_VIVA" "LINHAS_2009.LIN" "");;XXXXXXXXXXXXXX
(command "-linetype" "l" "CONTINUOUS" "LINHAS_2009.LIN" "");;XXXXXXXXXXXXXX
;(command "-linetype" "l" "DIQUE" "LINHAS_2009.LIN" "")
(command "-linetype" "l" "EIXO_PISTA" "LINHAS_2009.LIN" "");;XXXXXXXXXXXXXX
(command "-linetype" "l" "FERROVIA_BIT2" "LINHAS_2009.LIN" "");;XXXXXXXXXXX
(command "-linetype" "l" "FERROVIA" "LINHAS_2009.LIN" "");;XXXXXXXXXXXXXXXX
(command "-linetype" "l" "GRELHA" "LINHAS_2009.LIN" "");;XXXXXXXXXXXXXXXXXX
(command "-linetype" "l" "GUARD_RAIL" "LINHAS_2009.LIN" "");;XXXXXXXXXXXXXX
(command "-linetype" "l" "HIDDEN" "LINHAS_2009.LIN" "");;XXXXXXXXXXXXXXXXXX
;(command "-linetype" "l" "LIM_BAIRRO" "LINHAS_2009.LIN" "")
;(command "-linetype" "l" "LIM_DISTRITAL" "LINHAS_2009.LIN" "")
;(command "-linetype" "l" "LIM_INTERNACIONAL" "LINHAS_2009.LIN" "")
;(command "-linetype" "l" "LIM_MUNICIPAL" "LINHAS_2009.LIN" "")
;(command "-linetype" "l" "LIM_PERURBANO" "LINHAS_2009.LIN" "")
;(command "-linetype" "l" "LIM_SETOR" "LINHAS_2009.LIN" "")
(command "-linetype" "l" "LINHA_TRANS" "LINHAS_2009.LIN" "");;XXXXXXXXXXXXXX
;(command "-linetype" "l" "LIXOMOVTERRA" "LINHAS_2009.LIN" "")
(command "-linetype" "l" "MURO_ARRIMO" "LINHAS_2009.LIN" "");;XXXXXXXXXXXXXX
(command "-linetype" "l" "PASSA_SUB" "LINHAS_2009.LIN" "");;XXXXXXXXXXXXXXXX
(command "-linetype" "l" "PROJECAO" "LINHAS_2009.LIN" "");;XXXXXXXXXXXXXXXXX
(command "-linetype" "l" "RIO_COR_INT" "LINHAS_2009.LIN" "");;XXXXXXXXXXXXXX
(command "-linetype" "l" "RUINA_CASAC" "LINHAS_2009.LIN" "");;XXXXXXXXXXXXXX
(command "-linetype" "l" "TUNEL" "LINHAS_2009.LIN" "");;XXXXXXXXXXXXXXXXXXXX
(command "-linetype" "l" "VALA" "LINHAS_2009.LIN" "");;XXXXXXXXXXXXXXXXXXXXX
;(command "-linetype" "l" "VEGETACAO" "LINHAS_2009.LIN" "")
(command "-linetype" "l" "VIA_CONST" "LINHAS_2009.LIN" "");;XXXXXXXXXXXXXXXX
(command "-linetype" "l" "VIA_NPAV" "LINHAS_2009.LIN" "");;XXXXXXXXXXXXXXXXX
;(command "-linetype" "l" "VIAPAV_ASF" "LINHAS_2009.LIN" "")
;(command "-linetype" "l" "VIAPAV_BLO" "LINHAS_2009.LIN" "")
;(command "-linetype" "l" "VIAPAV_PED" "LINHAS_2009.LIN" "")
(command "-linetype" "l" "REDE_ESGOTO" "LINHAS_2009.LIN" "");;XXXXXXXXXXXXXX
;(command "-linetype" "l" "REDE_ELET" "LINHAS_2009.LIN" "")

;*************************************************************
;********  Atribui cor, traço  aos layers criados ************
;*************************************************************
  
	(setq Lent_Base (length Tabela_Base))
	(setq Layer_Obj (tblnext "LAYER" T))
	(while Layer_Obj
	  	(setq n 0  XX T Layer_Name (cdr (assoc 2 Layer_Obj)))
		(while (and (< n Lent_Base) XX)
		        (setq Linha_Tabela_Base (nth n Tabela_Base))
			(if (= Layer_Name (nth 0 Linha_Tabela_Base))
			  	(progn
				  (setq XX nil)
				  (setq Layer_Color (cdr (assoc 62 Layer_Obj)))
				  (setq Layer_Ltype (cdr (assoc 6 Layer_Obj)))
				  (if (/= Layer_Color (nth 1 Linha_Tabela_Base))
				    (progn
				      (setq Layer_Obj (subst (cons 62 (nth 1 Linha_Tabela_Base)) (assoc 62 Layer_Obj) (entget (tblobjname "LAYER" Layer_Name))))
				      (entmod Layer_Obj)
				    )
				  )
				  (if (/= Layer_Ltype (nth 2 Linha_Tabela_Base))
				    (progn
				      (setq Layer_Obj (subst (cons 6 (nth 2 Linha_Tabela_Base)) (assoc 6 Layer_Obj) (entget (tblobjname "LAYER" Layer_Name))))
				      (entmod Layer_Obj)
				    )
				  )
				);; fim do progn
			 );; fim fo if
		         (setq n (1+ n))
		 ); fim do while
	  	 (if (and XX (/= Layer_Name "0")) (princ (strcat "*" Layer_Name ": não consta da tabela de padronização.") Log_File))
	         (setq Layer_Obj (tblnext "LAYER"))
	  );;fim do while

(princ)
(princ "Criação de Layers finalizada")
(princ)
(princ)
)
(princ "Digite cria_layers para executar")
