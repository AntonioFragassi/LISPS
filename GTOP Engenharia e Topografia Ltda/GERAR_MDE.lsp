;; DATA DE ATUALIZAÇÃO: 10/09/24
;; Correção do cálculo dos segundos nos azimutes
;; Alteração da variável ATTDIA para inserção aoutomática dos blocos atributados.
(defun azdt (ptorigem ptfim / zero No Eo Nf Ef delta_e delta_n angulo angrad angreal grau temp minuto segundo azimuteg)
  (setq zero 0.0)
  ;;(capaerre)
  (setq No (cadr ptorigem))
  (setq Eo (car ptorigem))
  (setq Nf (cadr ptfim))
  (setq Ef (car ptfim))
  (setq delta_e (- Ef Eo))
  (setq delta_n (- Nf No))
  (if (= delta_n zero)
    (setq angulo "0.0000")
  )
  (if (/= delta_n zero)
    (progn
      (setq angrad (/ delta_e delta_n))
      (setq angulo (angtos (atan angrad) 0 4))
    )
  )
  (setq angreal (atof angulo))
  (if (and (>= delta_e zero) (>= delta_n zero))
    ;; 1o Quadrante
    (progn
      (setq angreal (- 90 angreal))
    )
    (if	(and (>= delta_e zero) (<= delta_n zero))
      ;; 2o Quadrante
      (progn
		(setq angreal (- 270 angreal))
      )
   (if (and (<= delta_e zero) (<= delta_n zero))
	;; 3o Quadrante
	(progn
	  (setq angreal (- 270 angreal))
	)
	(if (and (<= delta_e zero) (>= delta_n zero))
	  ;; 4o Quadrante
	  (progn
	    (setq angreal (- 450 angreal))
	  )
	)
      )
    )
  )
	(setq grau (fix angreal))
	(setq temp (* 60 (- angreal grau)))
	(setq minuto (fix temp))
	(setq temp (* 60 (- temp minuto)))
	(setq segundo (fix temp))
	(setq grau (rtos grau 2 0))
	(setq minuto (rtos minuto 2 0))
	(setq segundo (rtos segundo 2 1))
	(setq azimuteg (strcat "IPDF Az= " grau "°" minuto "'" segundo "\""))
	(setq AA azimuteg)
)
(defun DesenharPolilinha (listCOORD / Coord1 pt i NV lstpontos)
	(setq oldangbase (getvar "angbase"))
	(setvar "angbase" 0)
	(setq oldattdia (getvar "attdia"))
	(setvar "attdia" 0)
	(setq oldangdir (getvar "angdir"))
	(setvar "angdir" 1)
	(setq oldosmode (getvar "osmode"))
	(setvar "osmode" 0)
	(command "_.layer" "m" "TOP-NOVO_PERIMETRO" "")
	(setq lstpontos (list))
	(setq NV (-(length listCOORD)1))
	(setq i 0)
	(while (<= i NV)
		(progn
			(setq Coord1 (nth i listCOORD))
			(setq pt (list (atof(rtos (car Coord1) 2 4)) (atof(rtos (cadr Coord1) 2 4))))
			(setq lstpontos (append lstpontos (list pt)))
			(setq i (1+ i))		
		)
	)
	(command "_.PLINE")
	(foreach n lstpontos
		 (command n)
	  )
	(command "")
	(setvar "angbase" oldangbase)
	(setvar "angdir" oldangdir)
	(setvar "osmode" oldosmode)
)
(defun TIRAREP (LISTA / P1 P2 i LISTA1)
	(setq LISTA1 (list))
	;(setq LISTA listCOORD)
	(setq Comp (length LISTA))
	(setq i 0)
	(while (< i (- Comp 1))
		(progn
		    (setq P2 (nth (+ i 1) LISTA))
			(setq P1 (nth i LISTA))
			(if (/= (distance P1 P2) 0.0)
				(progn
					(setq LISTA1 (append  LISTA1 (list(nth i LISTA))))
				)
			)
		(setq i (+ i 1))
		)MDE
		
	)
	(setq LISTA1 (append  LISTA1 (list(nth 0 LISTA1))))
	(setq Res LISTA1)
)
(defun MAIORN ( LISTA / N posim i LISTA1 LISTA2)
	(setq LISTA1 (list))
	(setq LISTA2 (list))
	;(setq LISTA listCOORD)
	(setq Comp (length LISTA))
	(setq i 0)
	(setq posim 0)
	(while (< i (- Comp 1))
		(progn
			(if (> (cadr(nth (+ i 1) LISTA)) (cadr(nth posim LISTA)))
				(progn
					(setq posim (+ i 1))
				)
			)
		(setq i (+ i 1))
		)
	)
	(setq i posim)
	(while (< i Comp)
		(progn
			(setq LISTA1(append LISTA1 (list(nth i LISTA))))
		(setq i (+ i 1))
		)
	)
	(setq i 1)
	(while (<= i posim)
		(progn
			(setq LISTA2(append LISTA2 (list(nth i LISTA))))
		(setq i (+ i 1))
		)
	)
	(setq LISTA (list))
	(setq LISTA (append LISTA LISTA1))
	(setq LISTA (append LISTA LISTA2))
	(setq Res LISTA)
)
(defun CALCDH (P1 P2 / PT1 PT2 X1 Y1 X2 Y2 delta_n delta_e )
    (setq X1 (nth 0 P1))
	(setq Y1 (nth 1 P1))
	(setq X2 (nth 0 P2))
	(setq Y2 (nth 1 P2))
	(if (= PRECEN 11)
		(progn
			(setq X1 (atof(rtos X1 2 11)))
			(setq Y1 (atof(rtos Y1 2 11)))
			(setq X2 (atof(rtos X2 2 11)))
			(setq Y2 (atof(rtos Y2 2 11)))
		)
		(progn
			(setq X1 (atof(rtos X1 2 4)))
			(setq Y1 (atof(rtos Y1 2 4)))
			(setq X2 (atof(rtos X2 2 4)))
			(setq Y2 (atof(rtos Y2 2 4)))
		)
	)
	(setq PT1 (list X1 Y1))
	(setq PT2 (list X2 Y2))
	(cond ((= PRECDH  0) (setq Res (rtos ( / (distance PT1 PT2) KR) 2 0)))
       ((= PRECDH  1) (setq Res (rtos ( / (distance PT1 PT2) KR) 2 1)))
       ((= PRECDH  2) (setq Res (rtos ( / (distance PT1 PT2) KR) 2 2)))
       ((= PRECDH  3) (setq Res (rtos ( / (distance PT1 PT2) KR) 2 3)))
    )
)
(defun quadrante (P1 P2 / delta_e delta_n )
    (setq delta_n (- (nth 1 P2) (nth 1 P1)))
    (setq delta_e (- (nth 0 P2) (nth 0 P1)))
		(if (and (>= delta_e zero) (>= delta_n zero)) ;; 1o Quadrante
			(setq Res 1)
		  (if (and (>= delta_e zero) (<= delta_n zero)) ; 2o Quadrante
			(setq Res 2)
				(if (and (<= delta_e zero) (<= delta_n zero));; 3o Quadrante
					  (setq Res 3)
				  (if (and (<= delta_e zero) (>= delta_n zero));; 4o Quadrante
						(setq Res 4)
				  )
				)
			  )
		)
)
(defun rtd (a)
   (/ (* a 180.0) pi)
)
(defun LEROY (/ regua h)
 (prompt "\nAJUSTA AS LETRAS COM O PADRAO LEROY")
 (initget 1 "40 50 60 80 100 120 140 175 200")
 (setq regua (atoi(getkword "\nTamanho da Regua (40 50 60 80 100 120 140 175 200): ")))
 (cond ((= regua  40) (setq h 1.0))
       ((= regua  50) (setq h 1.3))
       ((= regua  60) (setq h 1.6))
       ((= regua  80) (setq h 2.0))
       ((= regua 100) (setq h 2.5))
       ((= regua 120) (setq h 3.0))
       ((= regua 140) (setq h 3.5))
       ((= regua 175) (setq h 4.0))
       ((= regua 200) (setq h 4.5))
 )
 (setq fator (/ escala 1000.0))
 (if (< regua 201)
   (progn
	   (setvar "textsize" (* h fator))
	   ;(setvar "textsize" 1.6)
   )
  )
)
(defun C:ESCAD ( / angulo BB DS P1 P2 P3 NV i DX MEIO PT1 PT2 PT3 TXTAZ TXTDS)
(prompt "\nCalcula e escreve azimute e distancia.")
    (setq zero 0.0)
    (setq h (getvar "TEXTSIZE"))
    (initang)
	(setq NV (length listCOORD))
	(setq i 0)
	(command "_.layer" "m" "TOP-TXT_AZIMUTE_DISTANCIA" "")
	(command "_.layer" "m" "TOP-LINHA_CHAMADA" "")
	(setvar "osmode" 0)
	(while (< i (- NV 1))
	    (setq MEIO 0.0)
		(setvar "osmode" 0)
		(setq P1 (nth i listCOORD))
		(setq P2 (nth (+ i 1)listCOORD))
		;(setq pT1 (cal "P1+[,0]"))
		(command "_.zoom" "W" P1  P2 "")
		(setq TXTDS (tira_ponto(CALCDH P1 P2)))
		(if (= padrao "SIM")
			(progn(setq TXTAZ (azdt P1 P2)))
			(progn(setq TXTAZ (CALCAZ P1 P2)))
		)
		(resetang)
		(SETQ MEIO (cal "(P1+P2)/2"))
		;(setq BB (angle P1 P2))
		(setq BB (angle P1 P2))
		(setq DS (atof(CALCDH P1 P2)))
		(setq P3 (polar P1 BB (/ DS 2.0)))
		(setq angulo BB)
		(if (or (= (quadrante P1 P2) 3) (= (quadrante P1 P2) 4))
			(setq angulo (+ angulo PI))
		)
		(if (< (* 14 h) DS )
			(progn
			    (setvar "osmode" 0)
			    (command "_.layer" "m" "TOP-TXT_AZIMUTE_DISTANCIA" "")
				(command "TEXT"  "M" (polar P3 (rem (+ BB (/ PI 2.0))(* PI 2.0)) h) h (rtd angulo) TXTDS)
				(command "TEXT"  "M" (polar P3 (rem (+ BB (* PI 1.5))(* PI 2.0)) h) h (rtd angulo) TXTAZ)
			);;FIM DO ENTAO
			(progn
			    (setvar "osmode" 0)
				(setq PT3 (getpoint "\nOnde quer escrever?:"))
				(setq DX (- (car MEIO) (car PT3)))
				(command "_.layer" "m" "TOP-TXT_AZIMUTE_DISTANCIA" "")
				(command "_.TEXT" "M" pT3 h 0 TXTAZ)
				(setq PT3 (cal "PT3-[0,2*h]"))
				(command "_.TEXT" "M" pT3 h 0 TXTDS)
				(setq PT3 (cal "PT3+[-6*h,0.95*h]"))
				(setq pT1 (cal "pT3+[12*h,0]"))
				(command "_.layer" "m" "TOP-LINHA_CHAMADA" "")
				(setvar "osmode" 0)
				(command "_.Pline" pt1 pt3 "") 
				(if (> DX 0.0)
					(command "_.Pline" pt1 MEIO "")
					(command "_.Pline" pt3 MEIO "")
				)
			);;FIM DO SE NAO
		);;FIM DO IF
		(setq i (+ 1 i))
	)
)
(defun c:ESCNE( / pt pt1 pt2 ptaux i E E1 N N1 NV DX)
(prompt "\nEscreve as coordenadas de um ponto (2D).")
    (initang)
    (command "_.layer" "m" "TOP-TXT_COORDENADA" "")
    (setq h (getvar "TEXTSIZE"))
	(setq NV (length listCOORD))
	(setq i 0)
	(while (< i (- NV 1))
		(progn
		    (command "_.layer" "m" "TOP-TXT_COORDENADA" "")
			(setq pt (nth i listCOORD))
			(setq pt1 (cal "pt-[50,50]"))
			(setq pt2 (cal "pt+[50,50]"))
			(command "_.zoom" "W" pt1  pt2 "")
			(setq E (car pt))
			(setq E1 (TXTE E))
			(setq N (cadr pt))
			(setq N1 (TXTN N))
			(setq pt1 (getpoint "\nCoordenada N. Defina a origem."))
			(setq DX (- (car pt1) (car pt)))
			(setq pt2 (cal "pt1-[0,0.5*h]"))
			(setvar "osmode" 0)
			(command "_.TEXT" pt1 h 90 N1)
			(setq pt1 (cal "pt1-[0,2*h]"))
			(command "_.TEXT" pt1 h 90 E1)
			(command "_.layer" "m" "TOP-LINHA_CHAMADA" "")
			(setq pt1 (cal "pt2+[10*h,0]"))
			(setvar "osmode" 0)
			(command "_.Pline" pt1 pt2 "") 
			(setvar "osmode" 0)
			(if (> DX 0.0)
				(command "_.Pline" pt2 pt "")
				(command "_.Pline" pt1 pt "")
			)  
			(princ)
			(setq i (+ i 1))
		)
	)
)
(defun CALCAZ (P1 P2 / temp zero quadrante angrad AA No Eo Nf Ef delta_e delta_n angreal intsegundo)
		(setq zero 0.0)
		(initang)
		(setvar "osmode" 1)
		(setvar "osmode" 1)
		(if (= PRECEN 11)
			(progn
				(setq No (atof(rtos(cadr P1) 2 11)))
				(setq Eo (atof(rtos(car  P1) 2 11)))
				(setq Nf (atof(rtos(cadr P2) 2 11)))
				(setq Ef (atof(rtos(car  P2) 2 11)))
			)
			(progn
				(setq No (atof(rtos(cadr P1) 2 4)))
				(setq Eo (atof(rtos(car  P1) 2 4)))
				(setq Nf (atof(rtos(cadr P2) 2 4)))
				(setq Ef (atof(rtos(car  P2) 2 4)))
			)
		)
		(setq delta_e (- Ef Eo))
		(setq delta_n (- Nf No))
			(if (= delta_n zero)
				(setq AA "0.0000")
			 )
			(if (/= delta_n zero)
			   (progn 
			  (setq angrad (/ delta_e delta_n))
			  (setq AA (angtos (atan angrad) 0 11))
			   )
			)
		(setq angreal (atof AA))
			
		(if (and (>= delta_e zero) (>= delta_n zero)) ;; 1o Quadrante
		  (progn
			;(princ "\n 1o quadrante")
			(setq angreal (- 90 angreal))
			(setq quadrante 1)
		  )
		  (if (and (>= delta_e zero) (<= delta_n zero)) ; 2o Quadrante
				(progn
					;(princ "\n 2o quadrante")
					(setq angreal (- 270 angreal))
					(setq quadrante 2)
				)
				(if (and (<= delta_e zero) (<= delta_n zero));; 3o Quadrante
				  (progn
					  ;(princ "\n 3o quadrante")
					  (setq angreal (- 270 angreal))
					  (setq quadrante 3)
				  )
				  (if (and (<= delta_e zero) (>= delta_n zero));; 4o Quadrante
					(progn
						;(princ "\n 4o quadrante")
						(setq angreal (- 450 angreal))
						(setq quadrante 4)
					)
				  )
				)
			  )
		)
		(setq grau (fix angreal))
		(setq temp (* 60 (- angreal grau)))
		(setq minuto (fix temp))
		(setq temp (* 60 (- temp minuto)))
		(setq grau (rtos grau 2 0))
		(if (= (strlen grau) 1) (setq grau (strcat "0" grau)))
		(setq minuto (rtos minuto 2 0))
		(if (= (strlen minuto) 1) (setq minuto (strcat "0" minuto)))
		(setq segundo "")
		(if (= PRECAZ 0)
			 (progn
			     (setq segundo (rtos temp 2 0))
				 (if (= (strlen segundo) 1) (setq segundo (strcat "0" segundo)))
				 (if (= (strlen segundo) 0) (setq segundo "00"))
			 )
			 (progn
				(setq intsegundo (fix temp))
				(setq decsegundo (rtos( * (- temp intsegundo) 10) 2 0))
				(if (< intsegundo 10) (setq segundo (strcat "0" (rtos intsegundo 2 0)))(setq segundo (rtos intsegundo 2 0)))
				(if (= (strlen decsegundo) 0) (setq segundo (strcat segundo ",0")))
				(if (= (strlen decsegundo) 1) (setq segundo (strcat segundo "," decsegundo)))
			 )
		)
		;;(if (= (strlen (rtos decsegundo 2 0)) 2) (setq segundo (strcat segundo "," (rtos decsegundo 2 0))))
		(resetang)
		(initang)
		(princ)
		(setq AA (strcat grau "°" minuto "'" segundo "\""))	
)
(defun TXTE(E / E1)
    (setq E1 (rtos E 2 4)) 
	(if (= (strlen E1) 6) 
		(progn 
			(setq E1 (strcat E1 ".0000"))
		)
		(progn
			(setq E1 (strcat E1 "0000"))
			(setq E1 (substr E1 1 11))
		)
	)
    (setq E1 (strcat (substr E1 1 3) "." (substr E1 4 3) "," (substr E1 8 4) ))
	(setq Res E1)
)
(defun TXTN(N / N1)
    (setq N1 (rtos N 2 4))
	(if (= (strlen N1) 7) 
		(progn 
			(setq N1 (strcat N1 ".0000"))
		)
		(progn
			(setq N1 (strcat N1 "0000"))
			(setq N1 (substr N1 1 12))
		)
	)
    (setq N1 (strcat(substr N1 1 1) "." (substr N1 2 3) "." (substr N1 5 3) "," (substr N1 9 4) ))
	(setq Res N1)
)
(defun tira_ponto (TEXTO / AUX j txt )
  	(setq comp (strlen TEXTO))
        (setq j 0)
        (setq aux "")
        (repeat (strlen TEXTO)
	  	(setq txt (substr TEXTO (setq j(1+ j)) 1))
	        (cond
		  ((= txt ".") (setq AUX (strcat aux "," )))
	          ((/= txt ".") (setq AUX (strcat aux txt )))
		 )
	)
  	(setq aux aux)
 )
(defun initang ()
    (setvar "ANGBASE" (/ pi 2))  
    (setvar "ANGDIR" 1)   
    (setvar "AUNITS" 1)   ; grau,minuto,segundo
    (setvar "AUPREC" 5)   ; 
    (setvar "LUNITS" 2)   ; decimal
    (setvar "LUPREC" 4)   
)
(defun resetang ()
    (setvar "ANGBASE" 0.0)  
    (setvar "ANGDIR"    0)   
    (setvar "AUNITS"    0)
    (setvar "AUPREC"    0)   
    (setvar "LUNITS"    2)   
    (setvar "LUPREC"    4)   
)
(defun c:KR(/)
(princ "\nAtualizacao do KR.")
    (capaerre)
    (princ (strcat "\nEntre com KR <" (rtos KR 2 7) "> : "))
    (setq temp KR)
    (setq KR (getreal))
    (if (= KR nil) (setq KR temp))
    (SETVAR "USERR1" KR)
    (princ (strcat "\nKR atual ==> " (rtos KR 2 7)))
    (princ)
)
(defun capaerre(/)
    (if (< (GETVAR "USERR1") 1.0)
      (progn
	(setq KR 1.0000000)
	(princ "\nKR nao cadastrado!!!")
	(princ (strcat "\nEntre com KR <" (rtos KR 2 7) "> : "))
	(setq temp KR)
	(setq KR (getreal))
	(if (= KR nil) (setq KR temp))
	(princ (strcat "\nKR atual ==> " (rtos KR 2 7)))
	(SETVAR "USERR1" KR)
      )
    )

    (if (not KR)
      (progn
		(setq KR (GETVAR "USERR1"))
		(setq hakr 1)
      )
    )
    (princ (strcat "\nKR atual ==> " (rtos KR 2 7)))
    (princ)
)
(defun c:MDE ( / padrao perim1 LISTAUX lin NV nomearq pref nicial prefixo tipo Elemento listassoc Objeto Coord Coord1 CoordINI DH AZIMUTE)
	(princ "\n#########################################################################################\n")
	(princ "\n#########################################################################################\n")
	(princ "\n##################### O ponto mais ao NORTE é o início do perímetro   ###################\n")
	(princ "\n#####################  O arquivo TXT exportado está na mesma pasta    ###################\n")
	(princ "\n###  Inicialize a Calculadora - Digite CAL na barra de comamndos e encerre a mesma    ###\n")
	(princ "\n#########################################################################################\n")
	(princ "\n#########################################################################################\n")
	(setq hakr 0)
	(setq listaerro (list))
	(initget 7)
	(setq escala(getreal "Escala do desenho: "))
	;(setq escala 1000)
	(setq fator (/ escala 1000.0))
	(LEROY)
	(capaerre)
	(princ "\n")
	(setq nomearq (getstring "Fonerça o nome do arquivo de saída: "))
	(setq pref (getvar "dwgprefix"))
	(setq nomef (strcat pref nomearq ".txt"))
	;(setq prefixo (getstring "Fonerça o Prefixo da numeração dos pontos: "))
	(setq prefixo "P")
	(initget "SIM NAO")
	(setq padrao (strcase(getkword "Deseja trabalhar com o padrão IPDF: <SIM> ou <NAO> ")))
	(if (= padrao "SIM")
		(progn
			(setq PRECDH 3)
			(setq PRECAZ 1)
			(setq PRECEN 11)
		)
		(progn
			(initget 1 "0 1 2 3")
			(setq PRECDH (atoi(getkword "Fonerça a precisão de apresentação das distâncias: <0>, <1>, <2> ou <3> ")))
			(initget 1 "0 1")
			(setq PRECAZ (atoi(getkword "Fonerça a precisão de apresentação do azimutes: <0> ou <1> ")))
			(initget 1 "4 11")
			(setq PRECEN (atoi(getkword "Fonerça a precsisão dos pontos E e N nos cálculos: <4> ou <11> ")))
		)
	)
	(setq nicial 1)
	(setq nicial(- nicial 1))
	(initget "SIM NAO")
	(setq tipo (strcase(getkword "Deseja colocar pontos no desenho: <SIM> ou <NAO> ")))
	;(setq tipo "SIM")
	  ;;;;(if (=(findfile nomef) nomef) ((setq nomef (strcat pref "PolyExt" ".txt")))
	(setq arq (open nomef "a" ))
	(setq perim1 0.0)
	(if (setq Elemento (car(Entsel "\nClique polilinha a exportar:")))
		 (progn 
		      (command "_area" "_ENTITY" Elemento)
			  ;(setq AREA (setq AREA (getvar "area")))
    		  (setq AREA (tira_ponto(rtos (/(/ (getvar "area") (* kr kr)) 10000) 2 4)))
			  (setq AREA (strcat AREA "ha"))
    		  (setq PERIM (strcat (tira_ponto(rtos (/ (getvar "perimeter") kr) 2 3))"m"))
			  (setq listassoc (entget Elemento))
			  (setq Objeto (cdr(assoc 0 listassoc)))
			  (if (= Objeto "LWPOLYLINE")
				  (progn
							(setq NV (cdr(assoc 90 listassoc)))
							(setq listCOORD (list))
							(setq i 1)
							(while (<= i NV)
								(progn
									(setq assoc_10 (assoc 10 listassoc))
									(setq listCOORD (append listCOORD (list (cdr assoc_10))))
									(setq listassoc (member assoc_10 listassoc))
									(setq listassoc (cdr listassoc)) 
									(setq i (1+ i))									
								)
							)
							
							(setq LISTAUX listCOORD)
							(setq listCOORD (list))
							(setq listCOORD (TIRAREP LISTAUX))
							(setq LISTAUX listCOORD)
							(setq listCOORD (list))
							(setq listCOORD (MAIORN LISTAUX))
							(setq NV (length listCOORD))
							(setq i 1)
							(while (< i NV)
							   ;;(setq CoordINI(cdr assoc_10))
							   (progn
									(setq Coord (nth (- i 1) listCOORD))
									(setq Coord1 (nth i listCOORD))
									(setq DH (CALCDH Coord Coord1))
									(setq perim1 (+ perim1 (atof DH)))
									(if (< (atof DH) 0.0001) 
										(progn
											(setq erro (list(strcat "Existem pontos repetidos no perímetro. Vértice " (itoa i)" e Vértice " (itoa (+ 1 i)))))
											(setq listaerro (append listaerro erro))
										)
									 )
									(setq DH (tira_ponto DH))
									(if (= padrao "SIM")
										(progn
											(setq AZIMUTE (azdt Coord Coord1))
										)
										(progn
											(setq AZIMUTE (CALCAZ Coord Coord1))
										)
									)
									(setq lin (strcat (itoa i) ";" prefixo "-" (itoa (+ i nicial)) ";" (TXTN(cadr Coord)) ";" (TXTE(car Coord))))
									(write-line lin arq)	
									(setq lin (strcat "" ";" "" ";" "" ";" "" ";" DH ";" AZIMUTE))
									(write-line lin arq)									
									(setq pt (list (car Coord) (cadr Coord)))
									(setq DESC (strcat prefixo "-" (itoa (+ i nicial))))
									(if (= tipo "SIM")
									  (progn
										(command "_.layer" "m" "VERTICE" "")
										(command "_.insert" "C:\\GTOP\\APOIO\\Blocos\\TOPOGRAFIA\\INCRA_vertice_V.dwg" pt fator "" "0" DESC)
									  )
									)
									(setq i (1+ i))
									;;C:\GTOP\APOIO\Blocos\TOPOGRAFIA
									;;(command "_.insert" "C:\\GTOP\\APOIO\\Blocos\\TOPOGRAFIA\\SIMB_PONTO_1.dwg" pt fator "" "0" DESC)						
								);;fim do progn
							);; fim do while
							(setq Coord (nth (- i 1) listCOORD))
							(setq lin (strcat "1" ";" prefixo "-" "1" ";" (TXTN(cadr Coord)) ";" (TXTE(car Coord))))
							(write-line lin arq)
							(setq lin (strcat "Área topográfica: " AREA "    -     Perímetro topográfico: " (tira_ponto(rtos perim1 2 3)) "m"))
							(write-line lin arq)
				   );;fim do progn
			  );;fim do if
		  );fim do progn
	  );;fim do if
(close arq)
(if (= padrao "SIM")
	(progn
	 (setq tipo "NAO")
	)
	(progn
		(initget "SIM NAO")
		(setq tipo (Getstring "\nRedesenhar a poligonal? <SIM> ou <NAO> : "))
	)
)
(if (or (= tipo "SIM") (= tipo "sim"))
			(progn
			    (entdel Elemento)
				(DesenharPolilinha listCOORD)
			)
)
(princ "\n########################################################\n")
(princ "\n########################################################\n")
(princ (strcat "\n----->Informações escritas no arquivo " nomef "\n"))
(princ "\n########################################################\n")
(princ "\n########################################################\n")
(princ)
)
(princ "\nDigite 'MDE' para iniciar...'ESCNE' para escrever as coordenadas.....'ESCAD' para escrever os azimutes e distâncias.\n")
