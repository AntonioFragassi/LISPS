;; Coloca numero do lote com numeração sequencial
(defun LEROY (/ regua  )
 (prompt "\nAJUSTA AS LETRAS COM O PADRAO LEROY")
 (initget 1  "40 50 60 80 100 120 140 175 200")
 (setq regua (getint "\nTamanho da Regua (40 50 60 80 100 120 140 175 200): ")
       ESCALA (getreal "Escala do desenho: ")
 )
 (cond ((= regua  40) (setq h 1.0))
       ((= regua  50) (setq h 1.3))
       ((= regua  60) (setq h 1.6))
       ((= regua  80) (setq h 2.0))
       ((= regua 100) (setq h 2.5))
       ((= regua 120) (setq h 3.0))
       ((= regua 140) (setq h 3.5))
       ((= regua 175) (setq h 4.0))
       ((= regua 200) (setq h 4.5))
 )
 (setq fator (/ escala 1000.0))
 (if (< regua 201)
   (setvar "textsize" (* h fator))
   (setvar "textsize" 1.6)
  )
)

(defun c:NLOTE ( / fator raio olcmdecho escala ponto i PONTO DESC COTA ESCALA h)
	(setq oldangbase (getvar "angbase"))
	(setvar "angbase" 0)
	(setq oldangdir (getvar "angdir"))
	(setvar "angdir" 0)
        (setq PI 3.14159265358979323846264)
        (setq olcmdecho (getvar "cmdecho"))
        (setvar "cmdecho" 0) 
        (if (= ESCALA nil) (LEROY))
        (princ (strcat "\nEscala 1:" (rtos escala 2 0)))
        (setq i (getint "Número inicial: "))
        (setvar "osmode" 512)
        (setq ROTA (getangle "Escolha a rotação:"))
        (setq ROTA (/(* ROTA 180.0) PI))
	(setq raio (* h 1.25 fator))
	(while (setq Pto_bloco (Getpoint "Selecione o Ponto: " )) ;; primeiro while 
                (if (< i 10)
                  (setq DESC (strcat "0" (itoa i)))
                  (setq DESC (itoa i))
                ) 
	        (command "_.layer" "m" "TXT_LOTE_TOPOGRAFICO" "")
                (setvar "osmode" 0)
      		(command "_.TEXT" "j" "mc" Pto_bloco "" ROTA DESC)
		(command "_.circle" Pto_bloco raio)
                (setq i (1+ i))
                (setvar "osmode" 512)
	) ;;fim do primeiro if
	(setvar "cmdecho" olcmdecho)
	(princ)
)
(princ "\nDigite 'NLOTE' para iniciar")
