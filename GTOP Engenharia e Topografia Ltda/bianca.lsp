;; Coloca os blocos segundo a descrição 
(defun c:bianca(/)
(princ "********* Espere um pouco - processando dados  ***********")
(setq olcmdecho (getvar "cmdecho"))
(setvar "cmdecho" 0) 
(command "_.insert" "INCRA_vertice_V" "196121.5067,8264670.1033" "1" "" "0" "P31" "")
(command "_.insert" "INCRA_vertice_V" "196123.1165,8264658.4747" "1" "" "0" "P30" "")
(command "_.insert" "INCRA_vertice_V" "196125.7272,8264640.7676" "1" "" "0" "P29" "")
(command "_.insert" "INCRA_vertice_V" "196129.6244,8264617.0337" "1" "" "0" "P28" "")
(command "_.insert" "INCRA_vertice_V" "196130.1994,8264605.7652" "1" "" "0" "P27" "")
(command "_.insert" "INCRA_vertice_V" "196131.3513,8264587.6886" "1" "" "0" "P26" "")
(command "_.insert" "INCRA_vertice_V" "196131.818,8264569.5495" "1" "" "0" "P25" "")
(command "_.insert" "INCRA_vertice_V" "196131.3362,8264551.9938" "1" "" "0" "P24" "")
(command "_.insert" "INCRA_vertice_V" "196130.9378,8264533.917" "1" "" "0" "P23" "")
(command "_.insert" "INCRA_vertice_V" "196130.6281,8264519.548" "1" "" "0" "P22" "")
(command "_.insert" "INCRA_vertice_V" "196180.6274,8264530.1563" "1" "" "0" "P21" "")
(command "_.insert" "INCRA_vertice_V" "196199.4959,8264534.2502" "1" "" "0" "P20" "")
(command "_.insert" "INCRA_vertice_V" "196218.2377,8264538.3379" "1" "" "0" "P19" "")
(command "_.insert" "INCRA_vertice_V" "196220.2289,8264530.638" "1" "" "0" "P18" "")
(command "_.insert" "INCRA_vertice_V" "196226.955,8264506.6527" "1" "" "0" "P17" "")
(command "_.insert" "INCRA_vertice_V" "196231.8339,8264490.0791" "1" "" "0" "P16" "")
(command "_.insert" "INCRA_vertice_V" "196237.4392,8264470.986" "1" "" "0" "P15" "")
(command "_.insert" "INCRA_vertice_V" "196242.6317,8264453.9718" "1" "" "0" "P14" "")
(command "_.insert" "INCRA_vertice_V" "196271.9684,8264464.3031" "1" "" "0" "P13" "")
(command "_.insert" "INCRA_vertice_V" "196348.3078,8264491.8544" "1" "" "0" "P12" "")
(command "_.insert" "INCRA_vertice_V" "196372.0527,8264500.0275" "1" "" "0" "P11" "")
(command "_.insert" "INCRA_vertice_V" "196409.4835,8264513.1694" "1" "" "0" "P10" "")
(command "_.insert" "INCRA_vertice_V" "196575.9618,8264569.5113" "1" "" "0" "P9" "")
(command "_.insert" "INCRA_vertice_V" "196594.8765,8264576.1724" "1" "" "0" "A0D-M-1790" "")
(command "_.insert" "INCRA_vertice_V" "196597.4839,8264571.6103" "1" "" "0" "A0D-V-8006" "")
(command "_.insert" "INCRA_vertice_V" "196593.4639,8264570.2203" "1" "" "0" "A0D-V-0378" "")
(command "_.insert" "INCRA_vertice_V" "196054.6739,8264383.8603" "1" "" "0" "A0D-V-0377" "")
(command "_.insert" "INCRA_vertice_V" "196056.1539,8264378.5403" "1" "" "0" "CWM-V-0150" "")
(command "_.insert" "INCRA_vertice_V" "196025.0439,8264369.5003" "1" "" "0" "CWM-V-0149" "")
(command "_.insert" "INCRA_vertice_V" "196008.1539,8264362.4903" "1" "" "0" "CWM-V-0148" "")
(command "_.insert" "INCRA_vertice_V" "196001.5539,8264360.2503" "1" "" "0" "CWM-V-0146" "")
(command "_.insert" "INCRA_vertice_V" "196000.2739,8264361.0003" "1" "" "0" "CWM-V-0147" "")
(command "_.insert" "INCRA_vertice_V" "195963.5139,8264348.5803" "1" "" "0" "CWM-V-0145" "")
(command "_.insert" "INCRA_vertice_V" "195962.3639,8264351.9403" "1" "" "0" "CWM-V-0144" "")
(command "_.insert" "INCRA_vertice_V" "195952.92,8264348.68" "1" "" "0" "A0D-V-11099" "")
(command "_.insert" "INCRA_vertice_V" "195947.45,8264364.59" "1" "" "0" "A0D-M-10634" "")
(command "_.insert" "INCRA_vertice_V" "195941.2,8264382.68" "1" "" "0" "A0D-M-10633" "")
(command "_.insert" "INCRA_vertice_V" "195934.35,8264402.58" "1" "" "0" "A0D-M-10632" "")
(command "_.insert" "INCRA_vertice_V" "195927.04,8264423.64" "1" "" "0" "A0D-M-10631" "")
(command "_.insert" "INCRA_vertice_V" "195920.6,8264442.46" "1" "" "0" "A0D-M-10630" "")
(command "_.insert" "INCRA_vertice_V" "195913.65,8264462.88" "1" "" "0" "A0D-M-10629" "")
(command "_.insert" "INCRA_vertice_V" "195905.83,8264485.32" "1" "" "0" "A0D-M-10628" "")
(command "_.insert" "INCRA_vertice_V" "195896.2,8264514.19" "1" "" "0" "A0D-M-9971" "")
(command "_.insert" "INCRA_vertice_V" "195896.2,8264514.19" "1" "" "0" "A0D-M-9971" "")
(command "_.insert" "INCRA_vertice_V" "195879.96,8264558.41" "1" "" "0" "A0D-M-9970" "")
(command "_.insert" "INCRA_vertice_V" "195884.49,8264559.53" "1" "" "0" "A0D-M-9969" "")
(command "_.insert" "INCRA_vertice_V" "195861.12,8264629.52" "1" "" "0" "A0D-M-2531" "")
(command "_.insert" "INCRA_vertice_V" "195888.75,8264638.75" "1" "" "0" "A0D-M-2530" "")
(command "_.insert" "INCRA_vertice_V" "195908.43,8264645.63" "1" "" "0" "A0D-M-2529" "")
(command "_.insert" "INCRA_vertice_V" "195909.35,8264645.94" "1" "" "0" "A0D-M-2528" "")
(command "_.insert" "INCRA_vertice_V" "195911.29,8264646.59" "1" "" "0" "A0D-M-2527" "")
(command "_.insert" "INCRA_vertice_V" "195914.87,8264647.84" "1" "" "0" "A0D-M-2526" "")
(command "_.insert" "INCRA_vertice_V" "195932.39,8264653.74" "1" "" "0" "A0D-M-2525" "")
(command "_.insert" "INCRA_vertice_V" "195946.37,8264658.37" "1" "" "0" "A0D-M-2524" "")
(command "_.insert" "INCRA_vertice_V" "195951.31,8264644.18" "1" "" "0" "A0D-M-2523" "")
(command "_.insert" "INCRA_vertice_V" "195956.58,8264628.5" "1" "" "0" "A0D-M-2522" "")
(command "_.insert" "INCRA_vertice_V" "195960.12,8264617.3" "1" "" "0" "A0D-V-5134" "")
(command "_.insert" "INCRA_vertice_V" "195944.99,8264614.02" "1" "" "0" "A0D-M-2521" "")
(command "_.insert" "INCRA_vertice_V" "195930.6,8264610.89" "1" "" "0" "A0D-M-2520" "")
(command "_.insert" "INCRA_vertice_V" "195932.7,8264603.78" "1" "" "0" "A0D-M-2519" "")
(command "_.insert" "INCRA_vertice_V" "195923.6,8264590.19" "1" "" "0" "A0D-M-2518" "")
(command "_.insert" "INCRA_vertice_V" "195923.4,8264583.34" "1" "" "0" "A0D-M-2517" "")
(command "_.insert" "INCRA_vertice_V" "195941.32,8264579.47" "1" "" "0" "A0D-M-2516" "")
(command "_.insert" "INCRA_vertice_V" "195956.89,8264576" "1" "" "0" "A0D-M-2515" "")
(command "_.insert" "INCRA_vertice_V" "195958.1,8264575.68" "1" "" "0" "A0D-M-2514" "")
(command "_.insert" "INCRA_vertice_V" "195957.16,8264571.65" "1" "" "0" "A0D-M-2513" "")
(command "_.insert" "INCRA_vertice_V" "195956.25,8264567.55" "1" "" "0" "A0D-M-2512" "")
(command "_.insert" "INCRA_vertice_V" "195955.92,8264565.88" "1" "" "0" "A0D-M-2511" "")
(command "_.insert" "INCRA_vertice_V" "195964.84,8264563.85" "1" "" "0" "A0D-M-2510" "")
(command "_.insert" "INCRA_vertice_V" "195963.54,8264552.3" "1" "" "0" "A0D-M-6000" "")
(command "_.insert" "INCRA_vertice_V" "195997.4139,8264548.6003" "1" "" "0" "A0D-M-1903" "")
(command "_.insert" "INCRA_vertice_V" "195997.9439,8264553.5703" "1" "" "0" "A0D-M-1902" "")
(command "_.insert" "INCRA_vertice_V" "196032.4339,8264549.9003" "1" "" "0" "A0D-M-1901" "")
(command "_.insert" "INCRA_vertice_V" "196041.5239,8264578.0103" "1" "" "0" "A0D-M-1900" "")
(command "_.insert" "INCRA_vertice_V" "196044.9339,8264588.5703" "1" "" "0" "A0D-M-1899" "")
(command "_.insert" "INCRA_vertice_V" "196050.7039,8264606.0503" "1" "" "0" "A0D-M-1898" "")
(command "_.insert" "INCRA_vertice_V" "196055.6039,8264627.3803" "1" "" "0" "A0D-M-1897" "")
(command "_.insert" "INCRA_vertice_V" "196059.0839,8264660.2903" "1" "" "0" "A0D-M-1896" "")
(command "_.insert" "INCRA_vertice_V" "196101.947,8264666.9865" "1" "" "0" "P33" "")
(command "_.insert" "INCRA_vertice_V" "196112.3131,8264668.6474" "1" "" "0" "P32" "")
(setvar "cmdecho" olcmdecho)
(setvar "clayer" oldlayer)
(princ)
)
(princ "\nDigite 'morada1' para iniciar")
