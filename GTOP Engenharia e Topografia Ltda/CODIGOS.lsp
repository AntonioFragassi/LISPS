;; Informa a descrição do código
(setq olcmdecho (getvar "cmdecho"))
(setvar "cmdecho" 0)
(defun c:COD ( / CODIGO)
(while (setq CODIGO (Getstring "\nDigite o código a procurar : "))
       (cond
                   ((= CODIGO "ADU")(PRINT "Adutora                     "))
                   ((= CODIGO "AFR")(PRINT "Afloramento Rochoso                     "))
                   ((= CODIGO "ALG")(PRINT "Alagado                     "))
                   ((= CODIGO "ALD")(PRINT "Alambrado                     "))
                   ((= CODIGO "ANT")(PRINT "Antena                     "))
                   ((= CODIGO "ATR")(PRINT "Antena de rádio                     "))
                   ((= CODIGO "ATP")(PRINT "Antena parabólica                     "))
                   ((= CODIGO "ARQ")(PRINT "Arquibancada                     "))
                   ((= CODIGO "ARC")(PRINT "Ar Condicionado                     "))
                   ((= CODIGO "ARV")(PRINT "Árvore                     "))
                   ((= CODIGO "ASP")(PRINT "Aspersor                     "))
                   ((= CODIGO "ATS")(PRINT "Aterro Sanitário                     "))
                   ((= CODIGO "BCR")(PRINT "Banca de revista                     "))
                   ((= CODIGO "BAP")(PRINT "Banco de praça                     "))
                   ((= CODIGO "BAF")(PRINT "Barraco de Ferro                     "))
                   ((= CODIGO "BAM")(PRINT "Barraco de Madeira                     "))
                   ((= CODIGO "BAR")(PRINT "Barragem de Concreto                     "))
                   ((= CODIGO "BPT")(PRINT "Barra de Proteção                     "))
                   ((= CODIGO "BEB")(PRINT "Bebedouro                     "))
                   ((= CODIGO "BLO")(PRINT "Boca de Lobo                     "))
                   ((= CODIGO "BLG")(PRINT "Boca de Lobo com Grelha                     "))
                   ((= CODIGO "BDA")(PRINT "Bomba d'Água                      "))
                   ((= CODIGO "BOA")(PRINT "Bomba de Alcool                     "))
                   ((= CODIGO "BOD")(PRINT "Bomba de Diesel                     "))
                   ((= CODIGO "BOG")(PRINT "Bomba de Gasolina                     "))
                   ((= CODIGO "BAC")(PRINT "Bordo do Acostamento                     "))
                   ((= CODIGO "BAS")(PRINT "Bordo do Asfalto                     "))
                   ((= CODIGO "BLC")(PRINT "Bloco de cimento (Passeios)                     "))
                   ((= CODIGO "BUE")(PRINT "Bueiro                     "))
                   ((= CODIGO "CAX")(PRINT "Caixa                     "))
                   ((= CODIGO "CAD")(PRINT "Caixa d'Água Domiciliar                     "))
                   ((= CODIGO "CXC")(PRINT "Caixa de Correio                     "))
                   ((= CODIGO "CAF")(PRINT "Caixa de Foça                     "))
                   ((= CODIGO "CIN")(PRINT "Caixa de Inspeção (Ñ Ident.)                     "))
                   ((= CODIGO "CIE")(PRINT "Caixa de Inspeção de Energia                     "))
                   ((= CODIGO "CIG")(PRINT "Caixa de Inspeção de esgoto                     "))
                   ((= CODIGO "CIT")(PRINT "Caixa de Inspeção de telefone                     "))
                   ((= CODIGO "CIP")(PRINT "Caixa Insp. Águas Pluv.                     "))
                   ((= CODIGO "CAL")(PRINT "Calçada                      "))
                   ((= CODIGO "CFU")(PRINT "Campo de futebol                     "))
                   ((= CODIGO "CMP")(PRINT "Campo de Pouso                     "))
                   ((= CODIGO "CAN")(PRINT "Canaleta/Canal                     "))
                   ((= CODIGO "CAN")(PRINT "Canil                     "))
                   ((= CODIGO "CCE")(PRINT "Canto de Cerca                     "))
                   ((= CODIGO "CCV")(PRINT "Canto de cerca viva                     "))
                   ((= CODIGO "CLM")(PRINT "Canto de Lote Materializado                     "))
                   ((= CODIGO "CMU")(PRINT "Canto de Muro                     "))
                   ((= CODIGO "CPE")(PRINT "Canto de prédio                     "))
                   ((= CODIGO "CQA")(PRINT "Canto de Quadra                     "))
                   ((= CODIGO "CAL")(PRINT "Casa de Alvenaria                     "))
                   ((= CODIGO "CAB")(PRINT "Casa de Bomba                     "))
                   ((= CODIGO "CMD")(PRINT "Casa de Madeira                     "))
                   ((= CODIGO "CER")(PRINT "Cerca                     "))
                   ((= CODIGO "CEM")(PRINT "Cerca Mista                     "))
                   ((= CODIGO "CEV")(PRINT "Cerca Viva                     "))
                   ((= CODIGO "CHQ")(PRINT "Chiqueiro                     "))
                   ((= CODIGO "CHU")(PRINT "Churrasqueira                     "))
                   ((= CODIGO "CHV")(PRINT "Chuveiro                     "))
                   ((= CODIGO "CIC")(PRINT "Ciclovia                     "))
                   ((= CODIGO "COL")(PRINT "Colchete                     "))
                   ((= CODIGO "CON ")(PRINT "Construção                     "))
                   ((= CODIGO "COQ")(PRINT "Coqueiro                     "))
                   ((= CODIGO "CRD")(PRINT "Corredeira                     "))
                   ((= CODIGO "COR")(PRINT "Córrego                     "))
                   ((= CODIGO "COS")(PRINT "Cota de soleira                     "))
                   ((= CODIGO "CRB")(PRINT "Crista Barranco/ Talude                     "))
                   ((= CODIGO "CUR")(PRINT "Curral                     "))
                   ((= CODIGO "DEG")(PRINT "Degrau                     "))
                   ((= CODIGO "DGP")(PRINT "Depósito de Gás                     "))
                   ((= CODIGO "DIQ")(PRINT "Diques                     "))
                   ((= CODIGO "EDF")(PRINT "Edificação                     "))
                   ((= CODIGO "EIP")(PRINT "Eixo da pista                     "))
                   ((= CODIGO "ERO")(PRINT "Erosão                     "))
                   ((= CODIGO "ESC")(PRINT "Escada                     "))
                   ((= CODIGO "EST")(PRINT "Estábulo                     "))
                   ((= CODIGO "ETA")(PRINT "Estaqueamento ou Estaca de Madeira                     "))
                   ((= CODIGO "EST")(PRINT "Estrada de Terra                     "))
                   ((= CODIGO "ETF")(PRINT "Estufa                     "))
                   ((= CODIGO "EUC")(PRINT "Eucalipto                     "))
                   ((= CODIGO "FER")(PRINT "Ferrovia                     "))
                   ((= CODIGO "FOS")(PRINT "Fossa                     "))
                   ((= CODIGO "FUG")(PRINT "Fundo ( Grota/ Córrego)                     "))
                   ((= CODIGO "GAH")(PRINT "Galinheiro                     "))
                   ((= CODIGO "GAA")(PRINT "Galpão de Alvenaria                     "))
                   ((= CODIGO "GAM")(PRINT "Galpão de Madeira                     "))
                   ((= CODIGO "GME")(PRINT "Galpão Metálico                     "))
                   ((= CODIGO "GAS")(PRINT "Gasoduto                     "))
                   ((= CODIGO "GEI")(PRINT "Geratriz inferior                     "))
                   ((= CODIGO "GES")(PRINT "Geratriz Superior                     "))
                   ((= CODIGO "GOB")(PRINT "Goiabeira                     "))
                   ((= CODIGO "GRD")(PRINT "Grade                     "))
                   ((= CODIGO "GRE")(PRINT "Grelha                     "))
                   ((= CODIGO "GRO")(PRINT "Grota                     "))
                   ((= CODIGO "GUR")(PRINT "Guard-Rail                     "))
                   ((= CODIGO "GAT")(PRINT "Guarita                     "))
                   ((= CODIGO "HID")(PRINT "Hidrante                      "))
                   ((= CODIGO "HOT")(PRINT "Horta                     "))
                   ((= CODIGO "JAD")(PRINT "Jardim                     "))
                   ((= CODIGO "LAG")(PRINT "Lago ou Lagoa                     "))
                   ((= CODIGO "LIV")(PRINT "Limite de Vegetação                     "))
                   ((= CODIGO "LIX")(PRINT "Lixeira                     "))
                   ((= CODIGO "LOT")(PRINT "Lote                     "))
                   ((= CODIGO "LUM")(PRINT "Luminária                     "))
                   ((= CODIGO "MAG")(PRINT "Mangueira                     "))
                   ((= CODIGO "MAC")(PRINT "Marco de Concreto                     "))
                   ((= CODIGO "MAM")(PRINT "Marco de Madeira                     "))
                   ((= CODIGO "MAB")(PRINT "Mata Burro                     "))
                   ((= CODIGO "MAT")(PRINT "Matacão ou pedra isolada                     "))
                   ((= CODIGO "MED")(PRINT "Medidor                     "))
                   ((= CODIGO "MFI")(PRINT "Meio Fio                     "))
                   ((= CODIGO "MNT")(PRINT "Monumentos                     "))
                   ((= CODIGO "MVT")(PRINT "Movimento de Terra                     "))
                   ((= CODIGO "MUR")(PRINT "Mureta                     "))
                   ((= CODIGO "MUU")(PRINT "Muro                     "))
                   ((= CODIGO "MAR")(PRINT "Muro de Arrimo                     "))
                   ((= CODIGO "MUP")(PRINT "Muro de Pedra                     "))
                   ((= CODIGO "MOR")(PRINT "Mourão de Madeira ou Concreto                     "))
                   ((= CODIGO "NAC")(PRINT "Nascente                     "))
                   ((= CODIGO "NVA")(PRINT "Nível d'água                      "))
                   ((= CODIGO "ORB")(PRINT "Orla do Brejo                     "))
                   ((= CODIGO "PAP")(PRINT "P.V de Águas Pluviais                     "))
                   ((= CODIGO "PEL")(PRINT "P.V de Eletricidade                     "))
                   ((= CODIGO "PES")(PRINT "P.V de Esgoto                     "))
                   ((= CODIGO "PTT")(PRINT "Pé da Torre de Transmisão                     "))
                   ((= CODIGO "PVN")(PRINT "P.V. não identificado                     "))
                   ((= CODIGO "PTL")(PRINT "P.V. Telefônico                     "))
                   ((= CODIGO "PAE")(PRINT "Padrão de energia                     "))
                   ((= CODIGO "PAL")(PRINT "Palmeira                     "))
                   ((= CODIGO "PEB")(PRINT "Pé Barranco/ Talude                     "))
                   ((= CODIGO "PIL")(PRINT "Pilar                     "))
                   ((= CODIGO "PIG")(PRINT "Pinguela                     "))
                   ((= CODIGO "PIQ")(PRINT "Piquete                     "))
                   ((= CODIGO "PSC")(PRINT "Piscina                     "))
                   ((= CODIGO "PIC")(PRINT "Pivô Central                     "))
                   ((= CODIGO "PLP")(PRINT "Placa de Propaganda                     "))
                   ((= CODIGO "PLS")(PRINT "Placa de Sinalização                     "))
                   ((= CODIGO "PLG")(PRINT "PlayGround                     "))
                   ((= CODIGO "POG")(PRINT "Pocilga                     "))
                   ((= CODIGO "POC")(PRINT "Poço                     "))
                   ((= CODIGO "PCA")(PRINT "Poço Artesiano                     "))
                   ((= CODIGO "PNT")(PRINT "Ponte                     "))
                   ((= CODIGO "PTO")(PRINT "Ponto Cotado                     "))
                   ((= CODIGO "PNO")(PRINT "Ponto de Ônibus                     "))
                   ((= CODIGO "PTX")(PRINT "Ponto de Taxi                     "))
                   ((= CODIGO "POR")(PRINT "Portão                     "))
                   ((= CODIGO "PTR")(PRINT "Poste com Transformador                     "))
                   ((= CODIGO "POC")(PRINT "Poste de Concreto                     "))
                   ((= CODIGO "POF")(PRINT "Poste de Ferrro                     "))
                   ((= CODIGO "POM")(PRINT "Poste de Madeira                     "))
                   ((= CODIGO "PRJ")(PRINT "Proj. do Telhado/Cobertura                     "))
                   ((= CODIGO "QUA")(PRINT "Quadra de Areia                     "))
                   ((= CODIGO "QUE")(PRINT "Quadra de Esporte                     "))
                   ((= CODIGO "QUQ")(PRINT "Quiosque                     "))
                   ((= CODIGO "RAP")(PRINT "Rede de Água Potavel                     "))
                   ((= CODIGO "RFL")(PRINT "Refletor                     "))
                   ((= CODIGO "REG")(PRINT "Registro d'Água                     "))
                   ((= CODIGO "RDA")(PRINT "Rego d'Água                     "))
                   ((= CODIGO "RES")(PRINT "Reservatório d'Água                     "))
                   ((= CODIGO "RII")(PRINT "Rio Intermitente                     "))
                   ((= CODIGO "RIP")(PRINT "Rio Perene                      "))
                   ((= CODIGO "SEM")(PRINT "Semáforo                     "))
                   ((= CODIGO "SUB")(PRINT "Subestação                     "))
                   ((= CODIGO "TOL")(PRINT "Toldo                     "))
                   ((= CODIGO "TNQ")(PRINT "Tanque                     "))
                   ((= CODIGO "TNA")(PRINT "Tanque de Alcool                     "))
                   ((= CODIGO "TND")(PRINT "Tanque de Diesel                     "))
                   ((= CODIGO "TNG")(PRINT "Tanque de Gasolina                     "))
                   ((= CODIGO "TAP")(PRINT "Tapume                     "))
                   ((= CODIGO "TUP")(PRINT "Telefone Público                     "))
                   ((= CODIGO "TOR")(PRINT "Torneira                     "))
                   ((= CODIGO "TAT")(PRINT "Torre de Alta Tensão                     "))
                   ((= CODIGO "VAL")(PRINT "Vala/Drenos                     "))
                   ((= CODIGO "VIC")(PRINT "Via em Construção                     "))
                   ((= CODIGO "VIP")(PRINT "Via Pavimentada                     "))
                   ((= CODIGO "VNP")(PRINT "Via Não Pavimentada                     "))
                   ((= CODIGO "VPA")(PRINT "Via Pavimentada Asfalto                     "))
                   ((= CODIGO "VPB")(PRINT "Via Pavimentada Bloquete                     "))
                   ((= CODIGO "VPP")(PRINT "Via Pavimentada Pedra                     "))
                   ((= CODIGO "VIV")(PRINT "Viveiro                     "))
                   (t (PROMPT "**** Código não cadastrado - Ver esse código ****"))
             )
)
(setvar "cmdecho" olcmdecho)
)
(prompt "\nDigite 'COD' para iniciar")
