;; Coloca texto com o valor da elevação de uma curma de nível
;; Caso a curva não tenha elevação, zero, solicita elevação, coloca elevação na curva
;; e coloca texto.
;; é necessário utilizar o LEROY antes

(defun c:txtcota ( / Delta regua Ht oldangbase oldangdir oldosmode curva ptins Dados elev h cota ang oldlayer
nomeniv aux valor )

  (setq oldangbase (getvar "angbase"))
  (setvar "angbase" 0)
  (setq oldangdir (getvar "angdir"))
  (setvar "angdir" 1)
  (setq oldosmode (getvar "osmode"))
   (setvar "osmode" 0)
  (setq Escala (getint "Valor da Escala do projeto: " ) )
  (setq Delta (/ (* 0.3 Escala ) 1000))
  (princ "\nRéguas: <40>;<50>;<60>;<80>;<100>;<120>;<140>;<175>;<200>;<240>;<290>;<350>;<425>;<450>")
  (initget 7)
  (setq regua (getint "\nForneça a régua do desenho: "))
  (command "_.STYLE" "ROMANS" "ROMANS" "0" "1.0" "0" "" "" "")
  (cond
     	((= regua 40) (setq Ht 1.0))
     	((= regua 50) (setq Ht 1.3))
     	((= regua 60) (setq Ht 1.6))
     	((= regua 80) (setq Ht 2.0))
   	((= regua 100) (setq Ht 2.5))
        ((= regua 120) (setq Ht 3.0))
        ((= regua 140) (setq Ht 3.5))
        ((= regua 175) (setq Ht 4.0))
        ((= regua 200) (setq Ht 4.5))
        ((= regua 240) (setq Ht 6.0))
        ((= regua 290) (setq Ht 7.5))
        ((= regua 350) (setq Ht 9.0))
        ((= regua 425) (setq Ht 11.0))
        ((= regua 450) (setq Ht 13.0))
        (T otherwise (setq Ht 1.0))
  )
  (setq Ht (* Ht (/ Escala 1000.0)))
  (setvar "TEXTSIZE" Ht)
  (setq oldlayer (getvar "clayer"))
  (setq curva (entsel "Selecione a curva de nível."))
  (while curva
                        (setq previous (car curva))
        	           (setq ptins (car(cdr curva)))
	           (setq Dados (entget(car curva)))
                        (setq nomeniv (cdr(assoc 8 dados)))
                        (setq nomeniv (strcat "TOP-TXT_CURVAS DE NIVEL" ""))
                        (command "_.-Layer" "m" nomeniv "")
                        (setq Cota (cdr(assoc 38 Dados)))
                        (if (= cota nil)
                            (setq cota (last(cdr(assoc 10 Dados))))
                        )
                        (setq h (getvar "TEXTSIZE"))
                        (if ( = Cota 0)
                           (progn
                           	(print "/nEsta Curva está sem elevação. ")
        			(initget 7)
        			(setq Cota (getint "Forneça a cota da curva: "))
                                      (command "_.change" Previous "" "P" "E" Cota "" "")
                           );;fim do progn
                        );;fim do if
		(setq aux (atof (rtos Cota 2 0) ))
		(setq valor (abs (- cota aux)))
		( if (< valor 0.001)
      			(setq texto (rtos Cota 2 0) )
      			(setq texto (rtos Cota 2 1) )
		)
                        (command "_.text" "J" "ml" ptins h pause texto)
                        ;(setq previous (entlast))
                        ;(command "_.trim" previous "" curva "")	
                        (setq curva (entsel "Selecione a curva de nível."))
  );;fim while
  (setvar "angbase" oldangbase)
  (setvar "angdir" oldangdir)
  (setvar "osmode" oldosmode)
  (command "_.-Layer" "m" oldlayer "")
 (print "")
)
(print "Digite txtcota para executar")
