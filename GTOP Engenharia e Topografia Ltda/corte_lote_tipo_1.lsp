(defun c:corte_lote ( / lista P1 P2 P3 P4 P5 PC CORREC ss)
      	(setq oldangbase (getvar "angbase"));;correção 2
    	(setvar "angbase" 0.0)
    	(setq oldangdir (getvar "angdir"));;correção 2
    	(setvar "angdir" 0)
    	(setq oldosmode (getvar "osmode"))
    	(setvar "osmode" 0)
    	(setq oldcmdecho (getvar "cmdecho"))
    	(setvar "cmdecho" 0)
   	(setq P1 '(219858.9067  8291906.5595  0.0000) P2 '(219896.2473  8291904.5667  0.0000) P3 '(219893.5678  8291854.3571  0.0000) P4 '(219856.2272  8291856.3499  0.0000))
   	(setq PC '(219876.2373  8291880.4583 0.0000))
  	(setq LISTA (entget (car (entsel "/nClique no texto do lote a ser cortado."))))
	(setq P5 (cdr(assoc 10 LISTA)))
   	(setq CORREC (c:cal "P5 - PC")) (setq P1 (c:cal "P1 + CORREC")) (setq P2 (c:cal "P2 + CORREC")) (setq P3 (c:cal "P3 + CORREC")) (setq P4 (c:cal "P4 + CORREC"))
   	(command "_.pline" P1 P2 P3 P4 "c" "")
   	(setq ss (entlast))
   	(command "_.maptrim" "s" ss "n" "n" "o" "n" "y" "i" "y")
   	(command "_.zoom" "e" "")
   	(command "_.erase" ss "")
)
(princ "\nDigite 'corte_lote' para iniciar")
