(defun OCTANTE ( ANG / RESP )
    (cond
	((and (>= ANG 0.0)(< ANG 90.0)) (setq RESP ANG))
        ((and (>= ANG 90.0)(< ANG 180.0)) (setq RESP (- ANG 180.0)))
	((and (>= ANG 180.0)(< ANG 270.0)) (setq RESP (- ANG 180.0)))
	((and (>= ANG 270.0)(<= ANG 360.0)) (setq RESP (- ANG 360.0)))
    )
  (setq RESP RESP)
 )

(defun DADOS_BLOCO ( OBJETO / DADOS1 lista Attn Attv PONTO DESC COTA)
  (setq DADOS1 nil)
  (while (/= (cdr (assoc 0 (entget OBJETO))) "SEQEND")
        (setq OBJETO (entnext OBJETO))
  	(setq lista (entget OBJETO))
        (setq Attn (cdr (assoc 2 lista)))
  	(setq Attv (cdr (assoc 1 lista)))
        (cond
	  ((= Attn "PONTO" ) (setq PONTO Attv) )
          ((= Attn "DESC" ) (setq DESC Attv) )
          ((= Attn "COTA" ) (setq COTA Attv) )
	 )
    )  
  	(setq DADOS1 (append DADOS1 (list PONTO) (list DESC) (list COTA)))
        (setq DADOS1 DADOS1)
)

(defun DADOS_PV ( / ANG FLAG FLAG1 FLAG2 FLAG3 FLAG4 p1 TIPO TIPOCI) ;;
        (command "_.layer" "m" "PECAS_ESGOTO" "")
        (setq ANG (atof (angtos (angle Pto_PV Paux )0 12)))
	(setq TIPOCI (getint "\nCI de 40 ou 60?: "))
	(if (= TIPOCI 40)
		(command "_.insert" "F:\\Biblioteca CAD\\Blocos\\CAESB_NOVO\\CX40.dwg" Pto_PV "" "" (OCTANTE ANG) "" NOME_PV CODIGO MATERPV OBSERV "" "" "" "" (strcat "P= " "") "" "" "" "")
		(command "_.insert" "F:\\Biblioteca CAD\\Blocos\\CAESB_NOVO\\CX60.dwg" Pto_PV "" "" (OCTANTE ANG) "" NOME_PV CODIGO MATERPV OBSERV "" "" "" "" (strcat "P= " "") "" "" "" "")
	);;fim do if

 )

(defun DADOS_SETA ( / comp ANG1 pp1 pp2 pp3 DIST PTOMED lista)
        (setvar "osmode" 132)
    	(command "_.layer" "m" "REDE_ESGOTO" "")
        (princ "\nPonto final da rede condoninial.")
        (command "line" Pto_PV PAUSE  "")
        (command "_.change" "L" "" "P" "c" 2 "")
        (command "_.change" "L" "" "P" "LW" 0.30 "")
        (command "_.layer" "m" "TXT_PECAS_ESGOTO" "")
        (princ "\nPonto final da rede condoninial.")
        (setq lista (entget (entlast)))
        (setq Paux (cdr (assoc 11  lista)))
        (setvar "osmode" 0)
    	(setq DIST (DISTANCE Paux Pto_PV))
        (setq comp (- (strlen (rtos DIST 2 2)) 1))
        (setq pp2 (c:cal "[1.5,0.0,0.0] * comp"))
    	(setq PTOMED (c:cal "Paux + Pto_PV"))
    	(setq PTOMED (c:cal "PTOMED / 2"))
        (setq pp1 (getpoint "Onde quer escrever a distância da rede?:"))
	(setq ANG1 (atof (angtos (angle PTOMED pp1)0 12)))
	(cond
		    ((and (>= ANG1 0.0)(< ANG1 90.0)) (command "insert" "F:\\Biblioteca CAD\\Blocos\\CAESB_NOVO\\DISTD.dwg" pp1 "" "" ""  (rtos DIST 2 2) ""))
		    ((and (>= ANG1 90.0)(< ANG1 270.0)) (command "insert" "F:\\Biblioteca CAD\\Blocos\\CAESB_NOVO\\DISTE.dwg" pp1 "" "" "" (rtos DIST 2 2) ""))
	            ((and (>= ANG1 270.0)(< ANG1 360.0)) (command "insert" "F:\\Biblioteca CAD\\Blocos\\CAESB_NOVO\\DISTD.dwg" pp1 "" "" "" (rtos DIST 2 2) ""))
	);;fim do cond
  	(cond
		    ((and (>= ANG1 0.0)(< ANG1 90.0)) (setq pp3 (c:cal "pp1 + pp2")))
		    ((and (>= ANG1 90.0)(< ANG1 270.0)) (setq pp3 (c:cal "pp1 - pp2")))
	            ((and (>= ANG1 270.0)(< ANG1 360.0)) (setq pp3 (c:cal "pp1 + pp2")))
	);;fim do cond
        (command "_.layer" "m" "TXT_PECAS_ESGOTO" "")
      	(command "pline" PTOMED pp1 pp3 "")
        (command "_.change" "L" "" "P" "c" 1 "")
        (command "_.change" "L" "" "P" "LW" 0.15 "")
        (if (>= DIST 8.00)
		(progn
      			(command "_.layer" "m" "REDE_ESGOTO" "")
			(setq ANG1 (atof (angtos (angle PTOMED Paux)0 12)))
		        (command "insert" "F:\\Biblioteca CAD\\Blocos\\CAESB_NOVO\\SETA1.dwg" PTOMED 0.5 "" ANG1 "")
		  )
	  )
)

(defun PARTE1 ( / )
    (setq Pto_PV nil NOME_PV nil COTA_TP nil COTA_T nil COTA_F nil PROF nil COTA_DG1 nil COTA_DG2 nil COTA_DG3 nil COTA_DG4 nil ALT_CHA nil OBSERV nil MATERPV  nil)
    (setq Conjunto (ssget '((0 . "INSERT"))))
    (setq Comp_Conj (sslength Conjunto))
    (if (= (sslength Conjunto) 1)
	(progn
	      	(setq OBJETO (ssname Conjunto 0))
              	(setq DADOS (DADOS_BLOCO OBJETO))
              	(setq DESC (nth 1 DADOS))
		(setq Pto_PV (cdr (assoc 10 (entget OBJETO))))
        	(setq NOME_PV (getstring "\nForneça o número da CI: "))
        	(setq NOME_PV (strcase NOME_PV))
                (setq COTA_TP 0.0)
	  	(setq COTA_F 0.0)
         	(setq PROF 0.0)
                (setq ALT_CHA  0.0)
	        (setq COTA_DG1 0.0)
	    	(setq COTA_DG2 0.0)
	    	(setq COTA_DG3 0.0)
	    	(setq COTA_DG4 0.0)
                (setq MATERPV "C.A.")
                (setq OBSERV (getstring "\nDescreva a observação da Peça: "))
                (setq OBSERV (strcase OBSERV))
		(setq PV (list 	Pto_PV NOME_PV COTA_TP COTA_T COTA_F PROF COTA_DG1 COTA_DG2 COTA_DG3 COTA_DG4 ALT_CHA CODIGO OBSERV MATERPV))
	        (DADOS_SETA )
		(DADOS_PV)
	  );;fim do progn
          (progn
	  	(princ "\nO tamanho da seleção está errado. Tente de novo.")
	        (PARTE1)
	  );FIM
       );fim do progn
);;fim defum
(defun PARTE2 ( / )
    (while T
        (setq DIAM 100)
        (setq MATER "PVC")
        (PARTE1)
     );;fim do while  		
)

(defun c:CICASA ( / Conjunto LISTA_SETA TEXTO1 OBSERV CODIGO MATER MATERPV DIAM Comp_Conj Pto_PV CPD DESC COTA_PES COTA_DG1 COTA_DG2 COTA_DG3 COTA_DG4 COTA_F COTA_T COTA_TP NOME_PV ALT_CHA PROF p1 Paux PROF_Aux MSN1 DIST PTOMED DECLIV )
   (C:cal "1+1")
   (setq oldangbase (getvar "angbase"));;correção 2
   (setvar "angbase" 0.0)
   (setq oldangdir (getvar "angdir"));;correção 2
   (setvar "angdir" 0)
   (setq oldosmode (getvar "osmode"))
   (setvar "osmode" 0)
   (setq oldcmdecho (getvar "cmdecho"))
   (setvar "cmdecho" 0)
   (command "_.layer" "m" "PECAS_ESGOTO" "")
   (command "_.layer" "m" "TXT_PECAS_ESGOTO" "")
   (setq CODIGO (getstring "\nForneça o código da obra: "))
   (setq CODIGO (strcase CODIGO))
   (setq MSN1 "Selecione os pontos:")
   (princ MSN1)
   (PARTE1)
   (PARTE2)
   ;;(princ Conjunto)
   (setvar "osmode" oldosmode)
   (setvar "cmdecho" olcmdecho)
)

(princ "\nDigite 'CICASA' para iniciar")
