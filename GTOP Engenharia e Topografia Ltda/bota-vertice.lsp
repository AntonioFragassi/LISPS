;; Coloca os blocos segundo a descrição 
(defun c:botavertice(/)
(princ "********* Espere um pouco - processando dados  ***********")
(setq olcmdecho (getvar "cmdecho"))
(setvar "cmdecho" 0) 
(command "_.insert" "INCRA_vertice_V" "199962.25,8232054.72" "1" "" "0" "AOD-V-OSW0001" "")
(command "_.insert" "INCRA_vertice_V" "199978.84,8232053.43" "1" "" "0" "AOD-V-OSW0002" "")
(command "_.insert" "INCRA_vertice_V" "200056.77,8232031.52" "1" "" "0" "AOD-V-OSW0003" "")
(command "_.insert" "INCRA_vertice_V" "200089.91,8232017.25" "1" "" "0" "AOD-V-OSW0004" "")
(command "_.insert" "INCRA_vertice_V" "200101.53,8232008.64" "1" "" "0" "AOD-V-OSW0005" "")
(command "_.insert" "INCRA_vertice_V" "200133.74,8231972.49" "1" "" "0" "AOD-V-OSW0006" "")
(command "_.insert" "INCRA_vertice_V" "200139.42,8231965.19" "1" "" "0" "AOD-V-OSW0007" "")
(command "_.insert" "INCRA_vertice_V" "200147.85,8231944.72" "1" "" "0" "AOD-V-OSW0008" "")
(command "_.insert" "INCRA_vertice_V" "200152.33,8231940.65" "1" "" "0" "AOD-V-OSW0009" "")
(command "_.insert" "INCRA_vertice_V" "200170.02,8231931.59" "1" "" "0" "AOD-V-OSW0010" "")
(command "_.insert" "INCRA_vertice_V" "200193.41,8231926.58" "1" "" "0" "AOD-V-OSW0011" "")
(command "_.insert" "INCRA_vertice_V" "200226.25,8231920.76" "1" "" "0" "AOD-V-OSW0012" "")
(command "_.insert" "INCRA_vertice_V" "200250.02,8231911.27" "1" "" "0" "AOD-V-OSW0013" "")
(command "_.insert" "INCRA_vertice_V" "200267.29,8231907.8" "1" "" "0" "AOD-V-OSW0014" "")
(command "_.insert" "INCRA_vertice_V" "200274.95,8231904.4" "1" "" "0" "AOD-V-OSW0015" "")
(command "_.insert" "INCRA_vertice_V" "200306.87,8231869.25" "1" "" "0" "AOD-V-OSW0016" "")
(command "_.insert" "INCRA_vertice_V" "200310.41,8231866.14" "1" "" "0" "AOD-V-OSW0017" "")
(command "_.insert" "INCRA_vertice_V" "200319.41,8231863" "1" "" "0" "AOD-V-OSW0018" "")
(command "_.insert" "INCRA_vertice_V" "200316.66,8231846.37" "1" "" "0" "AOD-V-OSW0019" "")
(command "_.insert" "INCRA_vertice_V" "200313.88,8231838.83" "1" "" "0" "AOD-V-OSW0020" "")
(command "_.insert" "INCRA_vertice_V" "200301.07,8231824.98" "1" "" "0" "AOD-V-OSW0021" "")
(command "_.insert" "INCRA_vertice_V" "200289.84,8231805.57" "1" "" "0" "AOD-V-OSW0022" "")
(command "_.insert" "INCRA_vertice_V" "200279.43,8231791.78" "1" "" "0" "AOD-V-OSW0023" "")
(command "_.insert" "INCRA_vertice_V" "200264.01,8231775.7" "1" "" "0" "AOD-V-OSW0024" "")
(command "_.insert" "INCRA_vertice_V" "200250.1,8231763.97" "1" "" "0" "AOD-V-OSW0025" "")
(command "_.insert" "INCRA_vertice_V" "200204.63,8231729.12" "1" "" "0" "AOD-V-OSW0026" "")
(command "_.insert" "INCRA_vertice_V" "200171.74,8231706.98" "1" "" "0" "AOD-V-OSW0027" "")
(command "_.insert" "INCRA_vertice_V" "200152.59,8231701.54" "1" "" "0" "AOD-V-OSW0028" "")
(command "_.insert" "INCRA_vertice_V" "200107.97,8231690.25" "1" "" "0" "AOD-V-OSW0029" "")
(command "_.insert" "INCRA_vertice_V" "200084.88,8231681.08" "1" "" "0" "AOD-M-OSW0001" "")
(command "_.insert" "INCRA_vertice_V" "200054.36,8231649.33" "1" "" "0" "AOD-M-OSW0002" "")
(command "_.insert" "INCRA_vertice_V" "200028.85,8231627.24" "1" "" "0" "AOD-M-OSW0003" "")
(command "_.insert" "INCRA_vertice_V" "199880.58,8231498.49" "1" "" "0" "AOD-M-OSW0004" "")
(command "_.insert" "INCRA_vertice_V" "199803.32,8231431.04" "1" "" "0" "AOD-M-OSW0005" "")
(command "_.insert" "INCRA_vertice_V" "199797.03,8231424.89" "1" "" "0" "AOD-M-OSW0006" "")
(command "_.insert" "INCRA_vertice_V" "199796.75,8231424.56" "1" "" "0" "AOD-V-OSW0030" "")
(command "_.insert" "INCRA_vertice_V" "199792.13,8231429.25" "1" "" "0" "A0D-P-2606" "")
(command "_.insert" "INCRA_vertice_V" "199787.12,8231436.8" "1" "" "0" "A0D-M-1352" "")
(command "_.insert" "INCRA_vertice_V" "199780.17,8231447.27" "1" "" "0" "A0D-P-2605" "")
(command "_.insert" "INCRA_vertice_V" "199772.44,8231451.68" "1" "" "0" "A0D-M-1351" "")
(command "_.insert" "INCRA_vertice_V" "199726.93,8231404.62" "1" "" "0" "A0D-M-1367" "")
(command "_.insert" "INCRA_vertice_V" "199665.87,8231343.39" "1" "" "0" "A0D-M-1366" "")
(command "_.insert" "INCRA_vertice_V" "199656.31,8231331.21" "1" "" "0" "A0D-M-1365" "")
(command "_.insert" "INCRA_vertice_V" "199632.97,8231282.82" "1" "" "0" "A0D-M-1364" "")
(command "_.insert" "INCRA_vertice_V" "199550.27,8231116.06" "1" "" "0" "A0D-M-1363" "")
(command "_.insert" "INCRA_vertice_V" "199526.6,8231069.65" "1" "" "0" "A0D-M-1362" "")
(command "_.insert" "INCRA_vertice_V" "199520.06,8231052.77" "1" "" "0" "A0D-M-1361" "")
(command "_.insert" "INCRA_vertice_V" "199534.17,8231036.51" "1" "" "0" "A0D-P-2604" "")
(command "_.insert" "INCRA_vertice_V" "199547.15,8231023.14" "1" "" "0" "A0D-P-2603" "")
(command "_.insert" "INCRA_vertice_V" "199545.36,8231002.26" "1" "" "0" "A0D-P-2602" "")
(command "_.insert" "INCRA_vertice_V" "199549.49,8230986.48" "1" "" "0" "A0D-P-2601" "")
(command "_.insert" "INCRA_vertice_V" "199552.61,8230963.37" "1" "" "0" "A0D-P-2600" "")
(command "_.insert" "INCRA_vertice_V" "199553.61,8230941.18" "1" "" "0" "A0D-P-2599" "")
(command "_.insert" "INCRA_vertice_V" "199561.55,8230921.77" "1" "" "0" "A0D-P-2598" "")
(command "_.insert" "INCRA_vertice_V" "199571.64,8230899.21" "1" "" "0" "A0D-P-2597" "")
(command "_.insert" "INCRA_vertice_V" "199573.43,8230880.86" "1" "" "0" "A0D-P-2596" "")
(command "_.insert" "INCRA_vertice_V" "199570.29,8230847.15" "1" "" "0" "A0D-P-2595" "")
(command "_.insert" "INCRA_vertice_V" "199581.95,8230837.09" "1" "" "0" "A0D-P-2594" "")
(command "_.insert" "INCRA_vertice_V" "199585.08,8230817.52" "1" "" "0" "A0D-P-2593" "")
(command "_.insert" "INCRA_vertice_V" "199594.65,8230788.68" "1" "" "0" "A0D-P-2592" "")
(command "_.insert" "INCRA_vertice_V" "199604.77,8230769.11" "1" "" "0" "A0D-P-2591" "")
(command "_.insert" "INCRA_vertice_V" "199606.59,8230746.81" "1" "" "0" "A0D-P-2590" "")
(command "_.insert" "INCRA_vertice_V" "199609.5,8230726.21" "1" "" "0" "A0D-P-2589" "")
(command "_.insert" "INCRA_vertice_V" "199610.62,8230701.24" "1" "" "0" "A0D-P-2588" "")
(command "_.insert" "INCRA_vertice_V" "199610.23,8230687.26" "1" "" "0" "A0D-P-2587" "")
(command "_.insert" "INCRA_vertice_V" "199609.21,8230670.98" "1" "" "0" "A0D-P-2586" "")
(command "_.insert" "INCRA_vertice_V" "199610.58,8230648.44" "1" "" "0" "A0D-P-2585" "")
(command "_.insert" "INCRA_vertice_V" "199618.88,8230627.55" "1" "" "0" "A0D-P-2584" "")
(command "_.insert" "INCRA_vertice_V" "199625.91,8230605.15" "1" "" "0" "A0D-P-2583" "")
(command "_.insert" "INCRA_vertice_V" "199632.12,8230587.55" "1" "" "0" "A0D-P-2582" "")
(command "_.insert" "INCRA_vertice_V" "199633.98,8230553.98" "1" "" "0" "A0D-P-2581" "")
(command "_.insert" "INCRA_vertice_V" "199629.89,8230544.28" "1" "" "0" "A0D-P-2580" "")
(command "_.insert" "INCRA_vertice_V" "199622.77,8230528.92" "1" "" "0" "A0D-P-2579" "")
(command "_.insert" "INCRA_vertice_V" "199619.98,8230512.67" "1" "" "0" "A0D-P-2578" "")
(command "_.insert" "INCRA_vertice_V" "199615.49,8230495.23" "1" "" "0" "A0D-P-2577" "")
(command "_.insert" "INCRA_vertice_V" "199625.24,8230480.36" "1" "" "0" "A0D-P-2576" "")
(command "_.insert" "INCRA_vertice_V" "199634.84,8230463.36" "1" "" "0" "A0D-P-2575" "")
(command "_.insert" "INCRA_vertice_V" "199648.67,8230449.27" "1" "" "0" "A0D-P-2574" "")
(command "_.insert" "INCRA_vertice_V" "199659.73,8230439" "1" "" "0" "A0D-P-2573" "")
(command "_.insert" "INCRA_vertice_V" "199663.93,8230428.44" "1" "" "0" "A0D-P-2572" "")
(command "_.insert" "INCRA_vertice_V" "199665.34,8230413.28" "1" "" "0" "A0D-P-2571" "")
(command "_.insert" "INCRA_vertice_V" "199666.07,8230396.9" "1" "" "0" "A0D-P-2570" "")
(command "_.insert" "INCRA_vertice_V" "199671.3,8230384.41" "1" "" "0" "A0D-P-2569" "")
(command "_.insert" "INCRA_vertice_V" "199671.53,8230371.35" "1" "" "0" "A0D-P-2568" "")
(command "_.insert" "INCRA_vertice_V" "199677.02,8230366.71" "1" "" "0" "A0D-P-2567" "")
(command "_.insert" "INCRA_vertice_V" "199688.2,8230369.27" "1" "" "0" "A0D-P-2566" "")
(command "_.insert" "INCRA_vertice_V" "199697.21,8230368.22" "1" "" "0" "A0D-P-2565" "")
(command "_.insert" "INCRA_vertice_V" "199705.21,8230361.79" "1" "" "0" "A0D-P-2564" "")
(command "_.insert" "INCRA_vertice_V" "199708.1,8230352.45" "1" "" "0" "A0D-P-2563" "")
(command "_.insert" "INCRA_vertice_V" "199708.98,8230340.24" "1" "" "0" "A0D-P-2562" "")
(command "_.insert" "INCRA_vertice_V" "199707.84,8230327.53" "1" "" "0" "A0D-P-2561" "")
(command "_.insert" "INCRA_vertice_V" "199698.46,8230318.35" "1" "" "0" "A0D-P-2560" "")
(command "_.insert" "INCRA_vertice_V" "199701.2,8230309.5" "1" "" "0" "A0D-V-4043" "")
(command "_.insert" "INCRA_vertice_V" "199701.88,8230307.32" "1" "" "0" "A0D-P-2507" "")
(command "_.insert" "INCRA_vertice_V" "199709.9,8230303.89" "1" "" "0" "A0D-P-2506" "")
(command "_.insert" "INCRA_vertice_V" "199711.73,8230301.63" "1" "" "0" "A0D-P-2505" "")
(command "_.insert" "INCRA_vertice_V" "199718.37,8230288.19" "1" "" "0" "A0D-P-2504" "")
(command "_.insert" "INCRA_vertice_V" "199728.68,8230273.75" "1" "" "0" "A0D-P-1532" "")
(command "_.insert" "INCRA_vertice_V" "199716.49,8230281.18" "1" "" "0" "A0D-P-1531" "")
(command "_.insert" "INCRA_vertice_V" "199711.25,8230278.17" "1" "" "0" "A0D-P-1530" "")
(command "_.insert" "INCRA_vertice_V" "199707.49,8230278.38" "1" "" "0" "A0D-P-1529" "")
(command "_.insert" "INCRA_vertice_V" "199703.87,8230281.07" "1" "" "0" "A0D-P-1528" "")
(command "_.insert" "INCRA_vertice_V" "199699.83,8230287.12" "1" "" "0" "A0D-P-1527" "")
(command "_.insert" "INCRA_vertice_V" "199692.39,8230292.6" "1" "" "0" "A0D-P-1526" "")
(command "_.insert" "INCRA_vertice_V" "199686.11,8230294.69" "1" "" "0" "A0D-P-1525" "")
(command "_.insert" "INCRA_vertice_V" "199678.11,8230293.97" "1" "" "0" "A0D-P-1524" "")
(command "_.insert" "INCRA_vertice_V" "199674.18,8230291.76" "1" "" "0" "A0D-P-1523" "")
(command "_.insert" "INCRA_vertice_V" "199674.83,8230288.13" "1" "" "0" "A0D-P-1522" "")
(command "_.insert" "INCRA_vertice_V" "199682.24,8230280.8" "1" "" "0" "A0D-P-1521" "")
(command "_.insert" "INCRA_vertice_V" "199684.38,8230276.95" "1" "" "0" "A0D-P-1520" "")
(command "_.insert" "INCRA_vertice_V" "199679.44,8230276.49" "1" "" "0" "A0D-P-1519" "")
(command "_.insert" "INCRA_vertice_V" "199660.27,8230282.59" "1" "" "0" "A0D-P-1518" "")
(command "_.insert" "INCRA_vertice_V" "199650.7,8230281.44" "1" "" "0" "A0D-P-1517" "")
(command "_.insert" "INCRA_vertice_V" "199641.17,8230289.34" "1" "" "0" "A0D-P-1516" "")
(command "_.insert" "INCRA_vertice_V" "199637.83,8230295.77" "1" "" "0" "A0D-P-1515" "")
(command "_.insert" "INCRA_vertice_V" "199636.63,8230303.95" "1" "" "0" "A0D-P-1514" "")
(command "_.insert" "INCRA_vertice_V" "199647.72,8230302.86" "1" "" "0" "A0D-P-1513" "")
(command "_.insert" "INCRA_vertice_V" "199652.64,8230305.98" "1" "" "0" "A0D-P-1512" "")
(command "_.insert" "INCRA_vertice_V" "199645.69,8230313.12" "1" "" "0" "A0D-P-1511" "")
(command "_.insert" "INCRA_vertice_V" "199630.67,8230316.72" "1" "" "0" "A0D-P-1510" "")
(command "_.insert" "INCRA_vertice_V" "199625.27,8230316.11" "1" "" "0" "A0D-P-1509" "")
(command "_.insert" "INCRA_vertice_V" "199622.96,8230312.04" "1" "" "0" "A0D-P-1508" "")
(command "_.insert" "INCRA_vertice_V" "199615.7,8230309.41" "1" "" "0" "A0D-P-1507" "")
(command "_.insert" "INCRA_vertice_V" "199605.29,8230306.07" "1" "" "0" "A0D-P-1506" "")
(command "_.insert" "INCRA_vertice_V" "199600.92,8230302.84" "1" "" "0" "A0D-P-1505" "")
(command "_.insert" "INCRA_vertice_V" "199599,8230293.3" "1" "" "0" "A0D-P-1504" "")
(command "_.insert" "INCRA_vertice_V" "199596.67,8230286.58" "1" "" "0" "A0D-P-1503" "")
(command "_.insert" "INCRA_vertice_V" "199588.47,8230285.83" "1" "" "0" "A0D-P-1502" "")
(command "_.insert" "INCRA_vertice_V" "199581.22,8230287.88" "1" "" "0" "A0D-P-1501" "")
(command "_.insert" "INCRA_vertice_V" "199570.6,8230291.24" "1" "" "0" "A0D-P-1500" "")
(command "_.insert" "INCRA_vertice_V" "199562.53,8230288.94" "1" "" "0" "A0D-P-1499" "")
(command "_.insert" "INCRA_vertice_V" "199549.19,8230284.55" "1" "" "0" "A0D-P-1498" "")
(command "_.insert" "INCRA_vertice_V" "199543.72,8230284.07" "1" "" "0" "A0D-P-1497" "")
(command "_.insert" "INCRA_vertice_V" "199541.27,8230284.1" "1" "" "0" "A0D-P-1496" "")
(command "_.insert" "INCRA_vertice_V" "199529.23,8230286.53" "1" "" "0" "A0D-P-1495" "")
(command "_.insert" "INCRA_vertice_V" "199516.84,8230287.38" "1" "" "0" "A0D-P-1494" "")
(command "_.insert" "INCRA_vertice_V" "199514.48,8230287.05" "1" "" "0" "A0D-P-1493" "")
(command "_.insert" "INCRA_vertice_V" "199494.7,8230279.35" "1" "" "0" "A0D-P-1492" "")
(command "_.insert" "INCRA_vertice_V" "199487.82,8230270.8" "1" "" "0" "A0D-P-1491" "")
(command "_.insert" "INCRA_vertice_V" "199482.26,8230266.92" "1" "" "0" "A0D-P-1490" "")
(command "_.insert" "INCRA_vertice_V" "199474.33,8230268.12" "1" "" "0" "A0D-P-1489" "")
(command "_.insert" "INCRA_vertice_V" "199466.24,8230269.68" "1" "" "0" "A0D-P-1488" "")
(command "_.insert" "INCRA_vertice_V" "199461.77,8230268.91" "1" "" "0" "A0D-P-1487" "")
(command "_.insert" "INCRA_vertice_V" "199458.27,8230264.49" "1" "" "0" "A0D-P-1486" "")
(command "_.insert" "INCRA_vertice_V" "199458.32,8230259.51" "1" "" "0" "A0D-P-1485" "")
(command "_.insert" "INCRA_vertice_V" "199455.73,8230256.92" "1" "" "0" "A0D-P-1484" "")
(command "_.insert" "INCRA_vertice_V" "199452.31,8230256.86" "1" "" "0" "A0D-P-1483" "")
(command "_.insert" "INCRA_vertice_V" "199449,8230257.72" "1" "" "0" "A0D-P-1482" "")
(command "_.insert" "INCRA_vertice_V" "199445.22,8230257.75" "1" "" "0" "A0D-P-1481" "")
(command "_.insert" "INCRA_vertice_V" "199441.44,8230257.19" "1" "" "0" "A0D-P-1480" "")
(command "_.insert" "INCRA_vertice_V" "199440.4,8230256.85" "1" "" "0" "A0D-P-1479" "")
(command "_.insert" "INCRA_vertice_V" "199438.93,8230257.52" "1" "" "0" "A0D-P-1478" "")
(command "_.insert" "INCRA_vertice_V" "199435.2,8230258.09" "1" "" "0" "A0D-P-1477" "")
(command "_.insert" "INCRA_vertice_V" "199419.2,8230256.7" "1" "" "0" "A0D-P-1476" "")
(command "_.insert" "INCRA_vertice_V" "199417.57,8230256.83" "1" "" "0" "A0D-P-1475" "")
(command "_.insert" "INCRA_vertice_V" "199415.75,8230256.38" "1" "" "0" "A0D-P-1474" "")
(command "_.insert" "INCRA_vertice_V" "199409.23,8230251.83" "1" "" "0" "A0D-P-1473" "")
(command "_.insert" "INCRA_vertice_V" "199395.74,8230250.61" "1" "" "0" "A0D-P-1472" "")
(command "_.insert" "INCRA_vertice_V" "199391.26,8230251.31" "1" "" "0" "A0D-P-1471" "")
(command "_.insert" "INCRA_vertice_V" "199383.55,8230249.8" "1" "" "0" "A0D-P-1470" "")
(command "_.insert" "INCRA_vertice_V" "199378.26,8230244.32" "1" "" "0" "A0D-P-1469" "")
(command "_.insert" "INCRA_vertice_V" "199366.06,8230233.13" "1" "" "0" "A0D-P-1468" "")
(command "_.insert" "INCRA_vertice_V" "199362.25,8230236.39" "1" "" "0" "A0D-P-1467" "")
(command "_.insert" "INCRA_vertice_V" "199360.93,8230242.86" "1" "" "0" "A0D-P-1466" "")
(command "_.insert" "INCRA_vertice_V" "199355.21,8230243.26" "1" "" "0" "A0D-P-1465" "")
(command "_.insert" "INCRA_vertice_V" "199351.95,8230236.9" "1" "" "0" "A0D-P-1464" "")
(command "_.insert" "INCRA_vertice_V" "199344.12,8230225.19" "1" "" "0" "A0D-P-1463" "")
(command "_.insert" "INCRA_vertice_V" "199343.61,8230221.58" "1" "" "0" "A0D-P-1462" "")
(command "_.insert" "INCRA_vertice_V" "199342.67,8230217.68" "1" "" "0" "A0D-P-1461" "")
(command "_.insert" "INCRA_vertice_V" "199334.79,8230218.34" "1" "" "0" "A0D-P-1460" "")
(command "_.insert" "INCRA_vertice_V" "199328.54,8230221.1" "1" "" "0" "A0D-P-1459" "")
(command "_.insert" "INCRA_vertice_V" "199320.46,8230229.79" "1" "" "0" "A0D-P-1458" "")
(command "_.insert" "INCRA_vertice_V" "199311.87,8230234.78" "1" "" "0" "A0D-P-1457" "")
(command "_.insert" "INCRA_vertice_V" "199303.07,8230242.7" "1" "" "0" "A0D-P-1456" "")
(command "_.insert" "INCRA_vertice_V" "199293.19,8230245" "1" "" "0" "A0D-P-1455" "")
(command "_.insert" "INCRA_vertice_V" "199282.92,8230244.05" "1" "" "0" "A0D-P-1454" "")
(command "_.insert" "INCRA_vertice_V" "199273.67,8230245.23" "1" "" "0" "A0D-P-1453" "")
(command "_.insert" "INCRA_vertice_V" "199272.4,8230246.08" "1" "" "0" "A0D-P-1452" "")
(command "_.insert" "INCRA_vertice_V" "199267.15,8230245.65" "1" "" "0" "A0D-P-1451" "")
(command "_.insert" "INCRA_vertice_V" "199253.28,8230248.53" "1" "" "0" "A0D-P-1450" "")
(command "_.insert" "INCRA_vertice_V" "199250.17,8230246.39" "1" "" "0" "A0D-P-1449" "")
(command "_.insert" "INCRA_vertice_V" "199238.84,8230243.29" "1" "" "0" "A0D-P-1448" "")
(command "_.insert" "INCRA_vertice_V" "199237.14,8230247.68" "1" "" "0" "A0D-P-1447" "")
(command "_.insert" "INCRA_vertice_V" "199224.17,8230245.84" "1" "" "0" "A0D-P-1446" "")
(command "_.insert" "INCRA_vertice_V" "199216.02,8230243.83" "1" "" "0" "A0D-P-1445" "")
(command "_.insert" "INCRA_vertice_V" "199206.36,8230241.33" "1" "" "0" "A0D-P-1444" "")
(command "_.insert" "INCRA_vertice_V" "199201.93,8230235.76" "1" "" "0" "A0D-P-1443" "")
(command "_.insert" "INCRA_vertice_V" "199192.77,8230231.02" "1" "" "0" "A0D-P-1442" "")
(command "_.insert" "INCRA_vertice_V" "199189.79,8230232.74" "1" "" "0" "A0D-P-1441" "")
(command "_.insert" "INCRA_vertice_V" "199187.27,8230235.12" "1" "" "0" "A0D-P-1440" "")
(command "_.insert" "INCRA_vertice_V" "199174.65,8230231.28" "1" "" "0" "A0D-P-1439" "")
(command "_.insert" "INCRA_vertice_V" "199161.44,8230229.95" "1" "" "0" "A0D-P-1438" "")
(command "_.insert" "INCRA_vertice_V" "199149.8,8230226.07" "1" "" "0" "A0D-P-1437" "")
(command "_.insert" "INCRA_vertice_V" "199147.72,8230222.55" "1" "" "0" "A0D-P-1436" "")
(command "_.insert" "INCRA_vertice_V" "199143.54,8230219.28" "1" "" "0" "A0D-P-1435" "")
(command "_.insert" "INCRA_vertice_V" "199137.35,8230216.08" "1" "" "0" "A0D-P-1434" "")
(command "_.insert" "INCRA_vertice_V" "199124.19,8230213.75" "1" "" "0" "A0D-P-1433" "")
(command "_.insert" "INCRA_vertice_V" "199118.95,8230213.17" "1" "" "0" "A0D-P-1432" "")
(command "_.insert" "INCRA_vertice_V" "199112.4,8230210.51" "1" "" "0" "A0D-P-1431" "")
(command "_.insert" "INCRA_vertice_V" "199101.76,8230207.99" "1" "" "0" "A0D-P-1430" "")
(command "_.insert" "INCRA_vertice_V" "199091.8,8230203.58" "1" "" "0" "A0D-P-1429" "")
(command "_.insert" "INCRA_vertice_V" "199086.9,8230203.77" "1" "" "0" "A0D-P-1428" "")
(command "_.insert" "INCRA_vertice_V" "199080.4,8230202.89" "1" "" "0" "A0D-P-1427" "")
(command "_.insert" "INCRA_vertice_V" "199063.85,8230203.85" "1" "" "0" "A0D-P-1426" "")
(command "_.insert" "INCRA_vertice_V" "199056.39,8230205.59" "1" "" "0" "A0D-P-1425" "")
(command "_.insert" "INCRA_vertice_V" "199054.54,8230205.19" "1" "" "0" "AOD-V-OSW0031" "")
(command "_.insert" "INCRA_vertice_V" "199052.65,8230204.49" "1" "" "0" "AOD-V-OSW0032" "")
(command "_.insert" "INCRA_vertice_V" "199048.76,8230203.89" "1" "" "0" "AOD-V-OSW0033" "")
(command "_.insert" "INCRA_vertice_V" "199045.98,8230202.98" "1" "" "0" "AOD-V-OSW0034" "")
(command "_.insert" "INCRA_vertice_V" "199044.49,8230201.87" "1" "" "0" "AOD-V-OSW0035" "")
(command "_.insert" "INCRA_vertice_V" "199043.11,8230202.62" "1" "" "0" "AOD-V-OSW0036" "")
(command "_.insert" "INCRA_vertice_V" "199042.01,8230203.04" "1" "" "0" "AOD-V-OSW0037" "")
(command "_.insert" "INCRA_vertice_V" "199040.08,8230202.12" "1" "" "0" "AOD-V-OSW0038" "")
(command "_.insert" "INCRA_vertice_V" "199038.26,8230200.92" "1" "" "0" "AOD-V-OSW0039" "")
(command "_.insert" "INCRA_vertice_V" "199035.32,8230200.6" "1" "" "0" "AOD-V-OSW0040" "")
(command "_.insert" "INCRA_vertice_V" "199032.12,8230197.54" "1" "" "0" "AOD-V-OSW0041" "")
(command "_.insert" "INCRA_vertice_V" "199029.58,8230194.99" "1" "" "0" "AOD-V-OSW0042" "")
(command "_.insert" "INCRA_vertice_V" "199024.93,8230194.82" "1" "" "0" "AOD-V-OSW0043" "")
(command "_.insert" "INCRA_vertice_V" "199022.55,8230193.41" "1" "" "0" "AOD-V-OSW0044" "")
(command "_.insert" "INCRA_vertice_V" "199020.33,8230193.14" "1" "" "0" "AOD-V-OSW0045" "")
(command "_.insert" "INCRA_vertice_V" "199019.1,8230192.45" "1" "" "0" "AOD-V-OSW0046" "")
(command "_.insert" "INCRA_vertice_V" "199019.16,8230190.02" "1" "" "0" "AOD-V-OSW0047" "")
(command "_.insert" "INCRA_vertice_V" "199017.43,8230188.35" "1" "" "0" "AOD-V-OSW0048" "")
(command "_.insert" "INCRA_vertice_V" "199012.83,8230189.2" "1" "" "0" "AOD-V-OSW0049" "")
(command "_.insert" "INCRA_vertice_V" "199007.08,8230185.89" "1" "" "0" "AOD-V-OSW0050" "")
(command "_.insert" "INCRA_vertice_V" "199004.8,8230183.45" "1" "" "0" "AOD-V-OSW0051" "")
(command "_.insert" "INCRA_vertice_V" "199001.08,8230180.92" "1" "" "0" "AOD-V-OSW0052" "")
(command "_.insert" "INCRA_vertice_V" "199002.27,8230178.41" "1" "" "0" "AOD-V-OSW0053" "")
(command "_.insert" "INCRA_vertice_V" "199001.97,8230176.2" "1" "" "0" "AOD-V-OSW0054" "")
(command "_.insert" "INCRA_vertice_V" "198999.53,8230171.29" "1" "" "0" "AOD-V-OSW0055" "")
(command "_.insert" "INCRA_vertice_V" "198996.98,8230169.61" "1" "" "0" "AOD-V-OSW0056" "")
(command "_.insert" "INCRA_vertice_V" "198995.1,8230167.01" "1" "" "0" "AOD-V-OSW0057" "")
(command "_.insert" "INCRA_vertice_V" "198991.71,8230164.53" "1" "" "0" "AOD-V-OSW0058" "")
(command "_.insert" "INCRA_vertice_V" "198991.13,8230160.27" "1" "" "0" "AOD-V-OSW0059" "")
(command "_.insert" "INCRA_vertice_V" "198989.51,8230157.08" "1" "" "0" "AOD-V-OSW0060" "")
(command "_.insert" "INCRA_vertice_V" "198987.34,8230155.43" "1" "" "0" "AOD-V-OSW0061" "")
(command "_.insert" "INCRA_vertice_V" "198983.76,8230154.4" "1" "" "0" "AOD-V-OSW0062" "")
(command "_.insert" "INCRA_vertice_V" "198981.39,8230152.29" "1" "" "0" "AOD-V-OSW0063" "")
(command "_.insert" "INCRA_vertice_V" "198974.82,8230150.75" "1" "" "0" "AOD-V-OSW0064" "")
(command "_.insert" "INCRA_vertice_V" "198972.22,8230147.92" "1" "" "0" "AOD-V-OSW0065" "")
(command "_.insert" "INCRA_vertice_V" "198962.64,8230144.43" "1" "" "0" "AOD-V-OSW0066" "")
(command "_.insert" "INCRA_vertice_V" "198960.74,8230141.46" "1" "" "0" "AOD-V-OSW0067" "")
(command "_.insert" "INCRA_vertice_V" "198958.91,8230138.64" "1" "" "0" "AOD-V-OSW0068" "")
(command "_.insert" "INCRA_vertice_V" "198955.75,8230136.79" "1" "" "0" "AOD-V-OSW0069" "")
(command "_.insert" "INCRA_vertice_V" "198951.98,8230132.32" "1" "" "0" "AOD-V-OSW0070" "")
(command "_.insert" "INCRA_vertice_V" "198948.29,8230131.56" "1" "" "0" "AOD-V-OSW0071" "")
(command "_.insert" "INCRA_vertice_V" "198941.46,8230127.49" "1" "" "0" "AOD-V-OSW0072" "")
(command "_.insert" "INCRA_vertice_V" "198938.15,8230128.38" "1" "" "0" "AOD-V-OSW0073" "")
(command "_.insert" "INCRA_vertice_V" "198936.22,8230127.72" "1" "" "0" "AOD-V-OSW0074" "")
(command "_.insert" "INCRA_vertice_V" "198933.46,8230127.97" "1" "" "0" "AOD-V-OSW0075" "")
(command "_.insert" "INCRA_vertice_V" "198929.52,8230127.59" "1" "" "0" "AOD-V-OSW0076" "")
(command "_.insert" "INCRA_vertice_V" "198925.88,8230125.59" "1" "" "0" "AOD-V-OSW0077" "")
(command "_.insert" "INCRA_vertice_V" "198916.24,8230126.44" "1" "" "0" "AOD-V-OSW0078" "")
(command "_.insert" "INCRA_vertice_V" "198913.06,8230125.14" "1" "" "0" "AOD-V-OSW0079" "")
(command "_.insert" "INCRA_vertice_V" "198908.39,8230125.09" "1" "" "0" "AOD-V-OSW0080" "")
(command "_.insert" "INCRA_vertice_V" "198906.06,8230123.74" "1" "" "0" "AOD-V-OSW0081" "")
(command "_.insert" "INCRA_vertice_V" "198900.27,8230120.34" "1" "" "0" "AOD-V-OSW0082" "")
(command "_.insert" "INCRA_vertice_V" "198897.37,8230119.17" "1" "" "0" "AOD-V-OSW0083" "")
(command "_.insert" "INCRA_vertice_V" "198892.62,8230118.15" "1" "" "0" "AOD-V-OSW0084" "")
(command "_.insert" "INCRA_vertice_V" "198888.54,8230115.4" "1" "" "0" "AOD-V-OSW0085" "")
(command "_.insert" "INCRA_vertice_V" "198884.44,8230111.96" "1" "" "0" "AOD-V-OSW0086" "")
(command "_.insert" "INCRA_vertice_V" "198882.4,8230112.36" "1" "" "0" "AOD-V-OSW0087" "")
(command "_.insert" "INCRA_vertice_V" "198880.21,8230111.24" "1" "" "0" "AOD-V-OSW0088" "")
(command "_.insert" "INCRA_vertice_V" "198879.68,8230111.04" "1" "" "0" "AOD-M-OSW0007" "")
(command "_.insert" "INCRA_vertice_V" "198744.26,8230324.19" "1" "" "0" "AOD-V-OSW0089" "")
(command "_.insert" "INCRA_vertice_V" "198741.07,8230329.16" "1" "" "0" "AOD-V-OSW0090" "")
(command "_.insert" "INCRA_vertice_V" "198735.58,8230337.52" "1" "" "0" "AOD-V-OSW0091" "")
(command "_.insert" "INCRA_vertice_V" "198729.97,8230345.8" "1" "" "0" "AOD-V-OSW0092" "")
(command "_.insert" "INCRA_vertice_V" "198724.25,8230354.01" "1" "" "0" "AOD-V-OSW0093" "")
(command "_.insert" "INCRA_vertice_V" "198718.41,8230362.12" "1" "" "0" "AOD-V-OSW0094" "")
(command "_.insert" "INCRA_vertice_V" "198712.47,8230370.17" "1" "" "0" "AOD-V-OSW0095" "")
(command "_.insert" "INCRA_vertice_V" "198706.41,8230378.12" "1" "" "0" "AOD-V-OSW0096" "")
(command "_.insert" "INCRA_vertice_V" "198700.23,8230385.98" "1" "" "0" "AOD-V-OSW0097" "")
(command "_.insert" "INCRA_vertice_V" "198693.95,8230393.76" "1" "" "0" "AOD-V-OSW0098" "")
(command "_.insert" "INCRA_vertice_V" "198687.56,8230401.45" "1" "" "0" "AOD-V-OSW0099" "")
(command "_.insert" "INCRA_vertice_V" "198681.07,8230409.06" "1" "" "0" "AOD-V-OSW0100" "")
(command "_.insert" "INCRA_vertice_V" "198674.47,8230416.57" "1" "" "0" "AOD-V-OSW0101" "")
(command "_.insert" "INCRA_vertice_V" "198667.77,8230424" "1" "" "0" "AOD-V-OSW0102" "")
(command "_.insert" "INCRA_vertice_V" "198660.96,8230431.31" "1" "" "0" "AOD-V-OSW0103" "")
(command "_.insert" "INCRA_vertice_V" "198654.05,8230438.54" "1" "" "0" "AOD-V-OSW0104" "")
(command "_.insert" "INCRA_vertice_V" "198647.04,8230445.68" "1" "" "0" "AOD-V-OSW0105" "")
(command "_.insert" "INCRA_vertice_V" "198639.93,8230452.72" "1" "" "0" "AOD-V-OSW0106" "")
(command "_.insert" "INCRA_vertice_V" "198632.73,8230459.65" "1" "" "0" "AOD-V-OSW0107" "")
(command "_.insert" "INCRA_vertice_V" "198625.42,8230466.48" "1" "" "0" "AOD-V-OSW0108" "")
(command "_.insert" "INCRA_vertice_V" "198618.03,8230473.21" "1" "" "0" "AOD-V-OSW0109" "")
(command "_.insert" "INCRA_vertice_V" "198478.26,8230598.59" "1" "" "0" "AOD-V-OSW0110" "")
(command "_.insert" "INCRA_vertice_V" "198474.57,8230601.93" "1" "" "0" "AOD-V-OSW0111" "")
(command "_.insert" "INCRA_vertice_V" "198467.24,8230608.74" "1" "" "0" "AOD-V-OSW0112" "")
(command "_.insert" "INCRA_vertice_V" "198460.03,8230615.67" "1" "" "0" "AOD-V-OSW0113" "")
(command "_.insert" "INCRA_vertice_V" "198452.95,8230622.73" "1" "" "0" "AOD-V-OSW0114" "")
(command "_.insert" "INCRA_vertice_V" "198445.98,8230629.9" "1" "" "0" "AOD-V-OSW0115" "")
(command "_.insert" "INCRA_vertice_V" "198439.14,8230637.2" "1" "" "0" "AOD-V-OSW0116" "")
(command "_.insert" "INCRA_vertice_V" "198432.43,8230644.61" "1" "" "0" "AOD-V-OSW0117" "")
(command "_.insert" "INCRA_vertice_V" "198425.85,8230652.14" "1" "" "0" "AOD-V-OSW0118" "")
(command "_.insert" "INCRA_vertice_V" "198419.4,8230659.79" "1" "" "0" "AOD-V-OSW0119" "")
(command "_.insert" "INCRA_vertice_V" "198413.09,8230667.54" "1" "" "0" "AOD-V-OSW0120" "")
(command "_.insert" "INCRA_vertice_V" "198406.91,8230675.4" "1" "" "0" "AOD-V-OSW0121" "")
(command "_.insert" "INCRA_vertice_V" "198400.87,8230683.37" "1" "" "0" "AOD-V-OSW0122" "")
(command "_.insert" "INCRA_vertice_V" "198394.96,8230691.44" "1" "" "0" "AOD-V-OSW0123" "")
(command "_.insert" "INCRA_vertice_V" "198389.2,8230699.61" "1" "" "0" "AOD-V-OSW0124" "")
(command "_.insert" "INCRA_vertice_V" "198383.58,8230707.88" "1" "" "0" "AOD-V-OSW0125" "")
(command "_.insert" "INCRA_vertice_V" "198378.1,8230716.25" "1" "" "0" "AOD-V-OSW0126" "")
(command "_.insert" "INCRA_vertice_V" "198372.77,8230724.71" "1" "" "0" "AOD-V-OSW0127" "")
(command "_.insert" "INCRA_vertice_V" "198350.65,8230760.5" "1" "" "0" "AOD-M-OSW0008" "")
(command "_.insert" "INCRA_vertice_V" "198379.76,8230793.55" "1" "" "0" "AOD-M-OSW0009" "")
(command "_.insert" "INCRA_vertice_V" "198421.9,8230782.9" "1" "" "0" "AOD-M-OSW0010" "")
(command "_.insert" "INCRA_vertice_V" "198434.23,8230779.68" "1" "" "0" "AOD-M-OSW0011" "")
(command "_.insert" "INCRA_vertice_V" "198437.24,8230779.5" "1" "" "0" "AOD-M-OSW0012" "")
(command "_.insert" "INCRA_vertice_V" "198440.36,8230779.97" "1" "" "0" "AOD-M-OSW0013" "")
(command "_.insert" "INCRA_vertice_V" "198469.15,8230789.86" "1" "" "0" "AOD-M-OSW0014" "")
(command "_.insert" "INCRA_vertice_V" "198502.33,8230801.54" "1" "" "0" "AOD-M-OSW0015" "")
(command "_.insert" "INCRA_vertice_V" "198505.65,8230801.6" "1" "" "0" "AOD-M-OSW0016" "")
(command "_.insert" "INCRA_vertice_V" "198520.57,8230801.21" "1" "" "0" "AOD-M-OSW0017" "")
(command "_.insert" "INCRA_vertice_V" "198563.89,8230801.71" "1" "" "0" "AOD-M-OSW0018" "")
(command "_.insert" "INCRA_vertice_V" "198605.61,8230800.31" "1" "" "0" "AOD-M-OSW0019" "")
(command "_.insert" "INCRA_vertice_V" "198624.33,8230809.99" "1" "" "0" "AOD-M-OSW0020" "")
(command "_.insert" "INCRA_vertice_V" "198640.5,8230823.11" "1" "" "0" "AOD-M-OSW0021" "")
(command "_.insert" "INCRA_vertice_V" "198662.75,8230840.91" "1" "" "0" "AOD-V-OSW0128" "")
(command "_.insert" "INCRA_vertice_V" "198663.98,8230839.83" "1" "" "0" "AOD-V-OSW0129" "")
(command "_.insert" "INCRA_vertice_V" "198664.34,8230837.74" "1" "" "0" "AOD-V-OSW0130" "")
(command "_.insert" "INCRA_vertice_V" "198665.3,8230836.03" "1" "" "0" "AOD-V-OSW0131" "")
(command "_.insert" "INCRA_vertice_V" "198666.83,8230835.04" "1" "" "0" "AOD-V-OSW0132" "")
(command "_.insert" "INCRA_vertice_V" "198669.16,8230834.1" "1" "" "0" "AOD-V-OSW0133" "")
(command "_.insert" "INCRA_vertice_V" "198671.3,8230832.65" "1" "" "0" "AOD-V-OSW0134" "")
(command "_.insert" "INCRA_vertice_V" "198672.37,8230832.38" "1" "" "0" "AOD-V-OSW0135" "")
(command "_.insert" "INCRA_vertice_V" "198674.26,8230832.23" "1" "" "0" "AOD-V-OSW0136" "")
(command "_.insert" "INCRA_vertice_V" "198674.79,8230832.08" "1" "" "0" "AOD-V-OSW0137" "")
(command "_.insert" "INCRA_vertice_V" "198676.89,8230825.49" "1" "" "0" "LBEL-V-0109" "")
(command "_.insert" "INCRA_vertice_V" "198702.61,8230800.83" "1" "" "0" "LBEL-V-0110" "")
(command "_.insert" "INCRA_vertice_V" "198709.02,8230810.39" "1" "" "0" "AOD-V-OSW0138" "")
(command "_.insert" "INCRA_vertice_V" "198709.28,8230810.03" "1" "" "0" "AOD-V-OSW0139" "")
(command "_.insert" "INCRA_vertice_V" "198709.7,8230809.75" "1" "" "0" "AOD-V-OSW0140" "")
(command "_.insert" "INCRA_vertice_V" "198710.14,8230809.49" "1" "" "0" "AOD-V-OSW0141" "")
(command "_.insert" "INCRA_vertice_V" "198710.45,8230809.15" "1" "" "0" "AOD-V-OSW0142" "")
(command "_.insert" "INCRA_vertice_V" "198710.77,8230808.53" "1" "" "0" "AOD-V-OSW0143" "")
(command "_.insert" "INCRA_vertice_V" "198711.12,8230807.74" "1" "" "0" "AOD-V-OSW0144" "")
(command "_.insert" "INCRA_vertice_V" "198711.36,8230807.1" "1" "" "0" "AOD-V-OSW0145" "")
(command "_.insert" "INCRA_vertice_V" "198711.59,8230806.65" "1" "" "0" "AOD-V-OSW0146" "")
(command "_.insert" "INCRA_vertice_V" "198711.9,8230806.25" "1" "" "0" "AOD-V-OSW0147" "")
(command "_.insert" "INCRA_vertice_V" "198712.08,8230806.07" "1" "" "0" "AOD-V-OSW0148" "")
(command "_.insert" "INCRA_vertice_V" "198712.35,8230805.8" "1" "" "0" "AOD-V-OSW0149" "")
(command "_.insert" "INCRA_vertice_V" "198712.65,8230805.59" "1" "" "0" "AOD-V-OSW0150" "")
(command "_.insert" "INCRA_vertice_V" "198713.3,8230805.24" "1" "" "0" "AOD-V-OSW0151" "")
(command "_.insert" "INCRA_vertice_V" "198713.58,8230805.01" "1" "" "0" "AOD-V-OSW0152" "")
(command "_.insert" "INCRA_vertice_V" "198713.69,8230804.87" "1" "" "0" "AOD-V-OSW0153" "")
(command "_.insert" "INCRA_vertice_V" "198713.91,8230804.42" "1" "" "0" "AOD-V-OSW0154" "")
(command "_.insert" "INCRA_vertice_V" "198714.24,8230803.84" "1" "" "0" "AOD-V-OSW0155" "")
(command "_.insert" "INCRA_vertice_V" "198714.73,8230803.17" "1" "" "0" "AOD-V-OSW0156" "")
(command "_.insert" "INCRA_vertice_V" "198715.09,8230802.8" "1" "" "0" "AOD-V-OSW0157" "")
(command "_.insert" "INCRA_vertice_V" "198715.53,8230802.33" "1" "" "0" "AOD-V-OSW0158" "")
(command "_.insert" "INCRA_vertice_V" "198715.84,8230801.8" "1" "" "0" "AOD-V-OSW0159" "")
(command "_.insert" "INCRA_vertice_V" "198716.1,8230801.24" "1" "" "0" "AOD-V-OSW0160" "")
(command "_.insert" "INCRA_vertice_V" "198716.61,8230800.23" "1" "" "0" "AOD-V-OSW0161" "")
(command "_.insert" "INCRA_vertice_V" "198717.23,8230799.32" "1" "" "0" "AOD-V-OSW0162" "")
(command "_.insert" "INCRA_vertice_V" "198717.76,8230798.73" "1" "" "0" "AOD-V-OSW0163" "")
(command "_.insert" "INCRA_vertice_V" "198718.57,8230797.97" "1" "" "0" "AOD-V-OSW0164" "")
(command "_.insert" "INCRA_vertice_V" "198719.05,8230797.68" "1" "" "0" "AOD-V-OSW0165" "")
(command "_.insert" "INCRA_vertice_V" "198719.78,8230797.46" "1" "" "0" "AOD-V-OSW0166" "")
(command "_.insert" "INCRA_vertice_V" "198720.16,8230797.39" "1" "" "0" "AOD-V-OSW0167" "")
(command "_.insert" "INCRA_vertice_V" "198720.71,8230797.4" "1" "" "0" "AOD-V-OSW0168" "")
(command "_.insert" "INCRA_vertice_V" "198720.97,8230797.36" "1" "" "0" "AOD-V-OSW0169" "")
(command "_.insert" "INCRA_vertice_V" "198721.21,8230797.24" "1" "" "0" "AOD-V-OSW0170" "")
(command "_.insert" "INCRA_vertice_V" "198721.62,8230796.91" "1" "" "0" "AOD-V-OSW0171" "")
(command "_.insert" "INCRA_vertice_V" "198721.83,8230796.66" "1" "" "0" "AOD-V-OSW0172" "")
(command "_.insert" "INCRA_vertice_V" "198722.16,8230796.1" "1" "" "0" "AOD-V-OSW0173" "")
(command "_.insert" "INCRA_vertice_V" "198722.57,8230795.45" "1" "" "0" "AOD-V-OSW0174" "")
(command "_.insert" "INCRA_vertice_V" "198723.02,8230794.74" "1" "" "0" "AOD-V-OSW0175" "")
(command "_.insert" "INCRA_vertice_V" "198723.53,8230794.09" "1" "" "0" "AOD-V-OSW0176" "")
(command "_.insert" "INCRA_vertice_V" "198723.92,8230793.77" "1" "" "0" "AOD-V-OSW0177" "")
(command "_.insert" "INCRA_vertice_V" "198724.43,8230793.55" "1" "" "0" "AOD-V-OSW0178" "")
(command "_.insert" "INCRA_vertice_V" "198725.31,8230793.41" "1" "" "0" "AOD-V-OSW0179" "")
(command "_.insert" "INCRA_vertice_V" "198725.93,8230793.38" "1" "" "0" "AOD-V-OSW0180" "")
(command "_.insert" "INCRA_vertice_V" "198726.83,8230793.3" "1" "" "0" "AOD-V-OSW0181" "")
(command "_.insert" "INCRA_vertice_V" "198727.41,8230793.22" "1" "" "0" "AOD-V-OSW0182" "")
(command "_.insert" "INCRA_vertice_V" "198727.65,8230793.11" "1" "" "0" "AOD-V-OSW0183" "")
(command "_.insert" "INCRA_vertice_V" "198727.95,8230792.73" "1" "" "0" "AOD-V-OSW0184" "")
(command "_.insert" "INCRA_vertice_V" "198728.11,8230792.22" "1" "" "0" "AOD-V-OSW0185" "")
(command "_.insert" "INCRA_vertice_V" "198728.24,8230791.68" "1" "" "0" "AOD-V-OSW0186" "")
(command "_.insert" "INCRA_vertice_V" "198728.45,8230791.21" "1" "" "0" "AOD-V-OSW0187" "")
(command "_.insert" "INCRA_vertice_V" "198729,8230790.5" "1" "" "0" "AOD-V-OSW0188" "")
(command "_.insert" "INCRA_vertice_V" "198730.25,8230789.19" "1" "" "0" "AOD-V-OSW0189" "")
(command "_.insert" "INCRA_vertice_V" "198731.59,8230787.8" "1" "" "0" "AOD-V-OSW0190" "")
(command "_.insert" "INCRA_vertice_V" "198732.55,8230786.73" "1" "" "0" "AOD-V-OSW0191" "")
(command "_.insert" "INCRA_vertice_V" "198733.39,8230785.9" "1" "" "0" "AOD-V-OSW0192" "")
(command "_.insert" "INCRA_vertice_V" "198734.42,8230785.34" "1" "" "0" "AOD-V-OSW0193" "")
(command "_.insert" "INCRA_vertice_V" "198735.85,8230784.87" "1" "" "0" "AOD-V-OSW0194" "")
(command "_.insert" "INCRA_vertice_V" "198737.06,8230784.53" "1" "" "0" "AOD-V-OSW0195" "")
(command "_.insert" "INCRA_vertice_V" "198738.26,8230784.19" "1" "" "0" "AOD-V-OSW0196" "")
(command "_.insert" "INCRA_vertice_V" "198738.72,8230783.84" "1" "" "0" "AOD-V-OSW0197" "")
(command "_.insert" "INCRA_vertice_V" "198739.14,8230783.11" "1" "" "0" "AOD-V-OSW0198" "")
(command "_.insert" "INCRA_vertice_V" "198739.44,8230782.25" "1" "" "0" "AOD-V-OSW0199" "")
(command "_.insert" "INCRA_vertice_V" "198739.7,8230781.45" "1" "" "0" "AOD-V-OSW0200" "")
(command "_.insert" "INCRA_vertice_V" "198739.98,8230781.22" "1" "" "0" "AOD-V-OSW0201" "")
(command "_.insert" "INCRA_vertice_V" "198740.58,8230780.95" "1" "" "0" "AOD-V-OSW0202" "")
(command "_.insert" "INCRA_vertice_V" "198741.63,8230780.68" "1" "" "0" "AOD-V-OSW0203" "")
(command "_.insert" "INCRA_vertice_V" "198742.7,8230780.47" "1" "" "0" "AOD-V-OSW0204" "")
(command "_.insert" "INCRA_vertice_V" "198744,8230780.1" "1" "" "0" "AOD-V-OSW0205" "")
(command "_.insert" "INCRA_vertice_V" "198745.59,8230779.55" "1" "" "0" "AOD-V-OSW0206" "")
(command "_.insert" "INCRA_vertice_V" "198746.87,8230778.98" "1" "" "0" "AOD-V-OSW0207" "")
(command "_.insert" "INCRA_vertice_V" "198747.93,8230778.23" "1" "" "0" "AOD-V-OSW0208" "")
(command "_.insert" "INCRA_vertice_V" "198749.18,8230776.8" "1" "" "0" "AOD-V-OSW0209" "")
(command "_.insert" "INCRA_vertice_V" "198750.22,8230776.01" "1" "" "0" "AOD-V-OSW0210" "")
(command "_.insert" "INCRA_vertice_V" "198751.68,8230775.28" "1" "" "0" "AOD-V-OSW0211" "")
(command "_.insert" "INCRA_vertice_V" "198753.06,8230774.94" "1" "" "0" "AOD-V-OSW0212" "")
(command "_.insert" "INCRA_vertice_V" "198755.09,8230774.31" "1" "" "0" "AOD-V-OSW0213" "")
(command "_.insert" "INCRA_vertice_V" "198756.62,8230773.89" "1" "" "0" "AOD-V-OSW0214" "")
(command "_.insert" "INCRA_vertice_V" "198758.17,8230773.71" "1" "" "0" "AOD-V-OSW0215" "")
(command "_.insert" "INCRA_vertice_V" "198759.03,8230773.75" "1" "" "0" "AOD-V-OSW0216" "")
(command "_.insert" "INCRA_vertice_V" "198760.01,8230773.44" "1" "" "0" "AOD-V-OSW0217" "")
(command "_.insert" "INCRA_vertice_V" "198761.01,8230773.18" "1" "" "0" "AOD-V-OSW0218" "")
(command "_.insert" "INCRA_vertice_V" "198761.98,8230773.27" "1" "" "0" "AOD-V-OSW0219" "")
(command "_.insert" "INCRA_vertice_V" "198762.93,8230773.8" "1" "" "0" "AOD-V-OSW0220" "")
(command "_.insert" "INCRA_vertice_V" "198763.45,8230774.5" "1" "" "0" "AOD-V-OSW0221" "")
(command "_.insert" "INCRA_vertice_V" "198764.36,8230775.64" "1" "" "0" "AOD-V-OSW0222" "")
(command "_.insert" "INCRA_vertice_V" "198765.17,8230776.63" "1" "" "0" "AOD-V-OSW0223" "")
(command "_.insert" "INCRA_vertice_V" "198765.51,8230776.88" "1" "" "0" "AOD-V-OSW0224" "")
(command "_.insert" "INCRA_vertice_V" "198766.07,8230777.02" "1" "" "0" "AOD-V-OSW0225" "")
(command "_.insert" "INCRA_vertice_V" "198767.84,8230777.27" "1" "" "0" "AOD-V-OSW0226" "")
(command "_.insert" "INCRA_vertice_V" "198769.1,8230777.44" "1" "" "0" "AOD-V-OSW0227" "")
(command "_.insert" "INCRA_vertice_V" "198769.91,8230777.46" "1" "" "0" "AOD-V-OSW0228" "")
(command "_.insert" "INCRA_vertice_V" "198770.71,8230777.21" "1" "" "0" "AOD-V-OSW0229" "")
(command "_.insert" "INCRA_vertice_V" "198771.7,8230776.75" "1" "" "0" "AOD-V-OSW0230" "")
(command "_.insert" "INCRA_vertice_V" "198772.59,8230776.52" "1" "" "0" "AOD-V-OSW0231" "")
(command "_.insert" "INCRA_vertice_V" "198773.71,8230776.23" "1" "" "0" "AOD-V-OSW0232" "")
(command "_.insert" "INCRA_vertice_V" "198775.06,8230775.86" "1" "" "0" "AOD-V-OSW0233" "")
(command "_.insert" "INCRA_vertice_V" "198776.24,8230775.81" "1" "" "0" "AOD-V-OSW0234" "")
(command "_.insert" "INCRA_vertice_V" "198777.66,8230776.07" "1" "" "0" "AOD-V-OSW0235" "")
(command "_.insert" "INCRA_vertice_V" "198779.57,8230776.49" "1" "" "0" "AOD-V-OSW0236" "")
(command "_.insert" "INCRA_vertice_V" "198781.12,8230776.81" "1" "" "0" "AOD-V-OSW0237" "")
(command "_.insert" "INCRA_vertice_V" "198782.32,8230776.82" "1" "" "0" "AOD-V-OSW0238" "")
(command "_.insert" "INCRA_vertice_V" "198783.55,8230776.22" "1" "" "0" "AOD-V-OSW0239" "")
(command "_.insert" "INCRA_vertice_V" "198785.28,8230775.19" "1" "" "0" "AOD-V-OSW0240" "")
(command "_.insert" "INCRA_vertice_V" "198787.45,8230773.82" "1" "" "0" "AOD-V-OSW0241" "")
(command "_.insert" "INCRA_vertice_V" "198789.51,8230772.35" "1" "" "0" "AOD-V-OSW0242" "")
(command "_.insert" "INCRA_vertice_V" "198791.25,8230771.17" "1" "" "0" "AOD-V-OSW0243" "")
(command "_.insert" "INCRA_vertice_V" "198792.71,8230770.42" "1" "" "0" "AOD-V-OSW0244" "")
(command "_.insert" "INCRA_vertice_V" "198794.41,8230769.93" "1" "" "0" "AOD-V-OSW0245" "")
(command "_.insert" "INCRA_vertice_V" "198795.52,8230769.45" "1" "" "0" "AOD-V-OSW0246" "")
(command "_.insert" "INCRA_vertice_V" "198796.24,8230768.52" "1" "" "0" "AOD-V-OSW0247" "")
(command "_.insert" "INCRA_vertice_V" "198796.54,8230767.79" "1" "" "0" "AOD-V-OSW0248" "")
(command "_.insert" "INCRA_vertice_V" "198796.99,8230767" "1" "" "0" "AOD-V-OSW0249" "")
(command "_.insert" "INCRA_vertice_V" "198797.66,8230766.01" "1" "" "0" "AOD-V-OSW0250" "")
(command "_.insert" "INCRA_vertice_V" "198797.77,8230765.41" "1" "" "0" "AOD-V-OSW0251" "")
(command "_.insert" "INCRA_vertice_V" "198797.66,8230764.49" "1" "" "0" "AOD-V-OSW0252" "")
(command "_.insert" "INCRA_vertice_V" "198797.61,8230763.48" "1" "" "0" "AOD-V-OSW0253" "")
(command "_.insert" "INCRA_vertice_V" "198797.77,8230761.84" "1" "" "0" "AOD-V-OSW0254" "")
(command "_.insert" "INCRA_vertice_V" "198798.11,8230759.89" "1" "" "0" "AOD-V-OSW0255" "")
(command "_.insert" "INCRA_vertice_V" "198798.43,8230758.61" "1" "" "0" "AOD-V-OSW0256" "")
(command "_.insert" "INCRA_vertice_V" "198799.31,8230757.17" "1" "" "0" "AOD-V-OSW0257" "")
(command "_.insert" "INCRA_vertice_V" "198800.25,8230756.3" "1" "" "0" "AOD-V-OSW0258" "")
(command "_.insert" "INCRA_vertice_V" "198801.37,8230755.73" "1" "" "0" "AOD-V-OSW0259" "")
(command "_.insert" "INCRA_vertice_V" "198802.48,8230755.32" "1" "" "0" "AOD-V-OSW0260" "")
(command "_.insert" "INCRA_vertice_V" "198803.97,8230754.7" "1" "" "0" "AOD-V-OSW0261" "")
(command "_.insert" "INCRA_vertice_V" "198805.62,8230753.92" "1" "" "0" "AOD-V-OSW0262" "")
(command "_.insert" "INCRA_vertice_V" "198806.7,8230753.66" "1" "" "0" "AOD-V-OSW0263" "")
(command "_.insert" "INCRA_vertice_V" "198808.39,8230753.63" "1" "" "0" "AOD-V-OSW0264" "")
(command "_.insert" "INCRA_vertice_V" "198810.6,8230753.94" "1" "" "0" "AOD-V-OSW0265" "")
(command "_.insert" "INCRA_vertice_V" "198812.66,8230754.59" "1" "" "0" "AOD-V-OSW0266" "")
(command "_.insert" "INCRA_vertice_V" "198814.71,8230755.32" "1" "" "0" "AOD-V-OSW0267" "")
(command "_.insert" "INCRA_vertice_V" "198817.38,8230756.09" "1" "" "0" "AOD-V-OSW0268" "")
(command "_.insert" "INCRA_vertice_V" "198818.72,8230756.47" "1" "" "0" "AOD-V-OSW0269" "")
(command "_.insert" "INCRA_vertice_V" "198819.84,8230757.46" "1" "" "0" "AOD-V-OSW0270" "")
(command "_.insert" "INCRA_vertice_V" "198821.53,8230758.66" "1" "" "0" "AOD-V-OSW0271" "")
(command "_.insert" "INCRA_vertice_V" "198822.94,8230759.33" "1" "" "0" "AOD-V-OSW0272" "")
(command "_.insert" "INCRA_vertice_V" "198824.43,8230759.84" "1" "" "0" "AOD-V-OSW0273" "")
(command "_.insert" "INCRA_vertice_V" "198825.74,8230760.56" "1" "" "0" "AOD-V-OSW0274" "")
(command "_.insert" "INCRA_vertice_V" "198827.12,8230761.14" "1" "" "0" "AOD-V-OSW0275" "")
(command "_.insert" "INCRA_vertice_V" "198828.05,8230761.33" "1" "" "0" "AOD-V-OSW0276" "")
(command "_.insert" "INCRA_vertice_V" "198828.58,8230761.17" "1" "" "0" "AOD-V-OSW0277" "")
(command "_.insert" "INCRA_vertice_V" "198829.23,8230760.53" "1" "" "0" "AOD-V-OSW0278" "")
(command "_.insert" "INCRA_vertice_V" "198829.94,8230759.65" "1" "" "0" "AOD-V-OSW0279" "")
(command "_.insert" "INCRA_vertice_V" "198830.41,8230758.88" "1" "" "0" "AOD-V-OSW0280" "")
(command "_.insert" "INCRA_vertice_V" "198830.89,8230758.52" "1" "" "0" "AOD-V-OSW0281" "")
(command "_.insert" "INCRA_vertice_V" "198831.76,8230758.51" "1" "" "0" "AOD-V-OSW0282" "")
(command "_.insert" "INCRA_vertice_V" "198832.65,8230758.75" "1" "" "0" "AOD-V-OSW0283" "")
(command "_.insert" "INCRA_vertice_V" "198833.9,8230759.5" "1" "" "0" "AOD-V-OSW0284" "")
(command "_.insert" "INCRA_vertice_V" "198835.46,8230760.25" "1" "" "0" "AOD-V-OSW0285" "")
(command "_.insert" "INCRA_vertice_V" "198837.35,8230760.99" "1" "" "0" "AOD-V-OSW0286" "")
(command "_.insert" "INCRA_vertice_V" "198838.74,8230761.32" "1" "" "0" "AOD-V-OSW0287" "")
(command "_.insert" "INCRA_vertice_V" "198839.55,8230761.35" "1" "" "0" "AOD-V-OSW0288" "")
(command "_.insert" "INCRA_vertice_V" "198840.1,8230761.14" "1" "" "0" "AOD-V-OSW0289" "")
(command "_.insert" "INCRA_vertice_V" "198840.75,8230760.3" "1" "" "0" "AOD-V-OSW0290" "")
(command "_.insert" "INCRA_vertice_V" "198841.57,8230759.29" "1" "" "0" "AOD-V-OSW0291" "")
(command "_.insert" "INCRA_vertice_V" "198842.64,8230758.36" "1" "" "0" "AOD-V-OSW0292" "")
(command "_.insert" "INCRA_vertice_V" "198843.97,8230757.58" "1" "" "0" "AOD-V-OSW0293" "")
(command "_.insert" "INCRA_vertice_V" "198845.53,8230756.9" "1" "" "0" "AOD-V-OSW0294" "")
(command "_.insert" "INCRA_vertice_V" "198846.73,8230756.46" "1" "" "0" "AOD-V-OSW0295" "")
(command "_.insert" "INCRA_vertice_V" "198848.33,8230755.86" "1" "" "0" "AOD-V-OSW0296" "")
(command "_.insert" "INCRA_vertice_V" "198850.37,8230754.76" "1" "" "0" "AOD-V-OSW0297" "")
(command "_.insert" "INCRA_vertice_V" "198851.72,8230753.68" "1" "" "0" "AOD-V-OSW0298" "")
(command "_.insert" "INCRA_vertice_V" "198852.7,8230752.44" "1" "" "0" "AOD-V-OSW0299" "")
(command "_.insert" "INCRA_vertice_V" "198853.74,8230751.27" "1" "" "0" "AOD-V-OSW0300" "")
(command "_.insert" "INCRA_vertice_V" "198855.02,8230750.46" "1" "" "0" "AOD-V-OSW0301" "")
(command "_.insert" "INCRA_vertice_V" "198856.61,8230749.79" "1" "" "0" "AOD-V-OSW0302" "")
(command "_.insert" "INCRA_vertice_V" "198857.69,8230749.51" "1" "" "0" "AOD-V-OSW0303" "")
(command "_.insert" "INCRA_vertice_V" "198858.93,8230749.25" "1" "" "0" "AOD-V-OSW0304" "")
(command "_.insert" "INCRA_vertice_V" "198859.87,8230748.7" "1" "" "0" "AOD-V-OSW0305" "")
(command "_.insert" "INCRA_vertice_V" "198860.45,8230748.09" "1" "" "0" "AOD-V-OSW0306" "")
(command "_.insert" "INCRA_vertice_V" "198861.2,8230747.08" "1" "" "0" "AOD-V-OSW0307" "")
(command "_.insert" "INCRA_vertice_V" "198862.01,8230746.19" "1" "" "0" "AOD-V-OSW0308" "")
(command "_.insert" "INCRA_vertice_V" "198862.99,8230745.25" "1" "" "0" "AOD-V-OSW0309" "")
(command "_.insert" "INCRA_vertice_V" "198863.75,8230744.44" "1" "" "0" "AOD-V-OSW0310" "")
(command "_.insert" "INCRA_vertice_V" "198864.34,8230743.72" "1" "" "0" "AOD-V-OSW0311" "")
(command "_.insert" "INCRA_vertice_V" "198865.06,8230742.75" "1" "" "0" "AOD-V-OSW0312" "")
(command "_.insert" "INCRA_vertice_V" "198865.57,8230742.32" "1" "" "0" "AOD-V-OSW0313" "")
(command "_.insert" "INCRA_vertice_V" "198867.03,8230741.49" "1" "" "0" "AOD-V-OSW0314" "")
(command "_.insert" "INCRA_vertice_V" "198868.5,8230740.35" "1" "" "0" "AOD-V-OSW0315" "")
(command "_.insert" "INCRA_vertice_V" "198869.52,8230739.27" "1" "" "0" "AOD-V-OSW0316" "")
(command "_.insert" "INCRA_vertice_V" "198870.06,8230738.21" "1" "" "0" "AOD-V-OSW0317" "")
(command "_.insert" "INCRA_vertice_V" "198870.56,8230737.12" "1" "" "0" "AOD-V-OSW0318" "")
(command "_.insert" "INCRA_vertice_V" "198870.99,8230736.59" "1" "" "0" "AOD-V-OSW0319" "")
(command "_.insert" "INCRA_vertice_V" "198871.63,8230736.09" "1" "" "0" "AOD-V-OSW0320" "")
(command "_.insert" "INCRA_vertice_V" "198872.7,8230735.43" "1" "" "0" "AOD-V-OSW0321" "")
(command "_.insert" "INCRA_vertice_V" "198873.6,8230734.65" "1" "" "0" "AOD-V-OSW0322" "")
(command "_.insert" "INCRA_vertice_V" "198874.13,8230733.61" "1" "" "0" "AOD-V-OSW0323" "")
(command "_.insert" "INCRA_vertice_V" "198874.39,8230732.84" "1" "" "0" "AOD-V-OSW0324" "")
(command "_.insert" "INCRA_vertice_V" "198874.79,8230731.7" "1" "" "0" "AOD-V-OSW0325" "")
(command "_.insert" "INCRA_vertice_V" "198875.53,8230730.54" "1" "" "0" "AOD-V-OSW0326" "")
(command "_.insert" "INCRA_vertice_V" "198876.85,8230729.04" "1" "" "0" "AOD-V-OSW0327" "")
(command "_.insert" "INCRA_vertice_V" "198877.86,8230727.93" "1" "" "0" "AOD-V-OSW0328" "")
(command "_.insert" "INCRA_vertice_V" "198879.24,8230726.21" "1" "" "0" "AOD-V-OSW0329" "")
(command "_.insert" "INCRA_vertice_V" "198880.66,8230724.53" "1" "" "0" "AOD-V-OSW0330" "")
(command "_.insert" "INCRA_vertice_V" "198882.36,8230722.87" "1" "" "0" "AOD-V-OSW0331" "")
(command "_.insert" "INCRA_vertice_V" "198883.78,8230721.4" "1" "" "0" "AOD-V-OSW0332" "")
(command "_.insert" "INCRA_vertice_V" "198884.5,8230720.71" "1" "" "0" "AOD-V-OSW0333" "")
(command "_.insert" "INCRA_vertice_V" "198885.73,8230719.68" "1" "" "0" "AOD-V-OSW0334" "")
(command "_.insert" "INCRA_vertice_V" "198886.76,8230718.57" "1" "" "0" "AOD-V-OSW0335" "")
(command "_.insert" "INCRA_vertice_V" "198887.34,8230717.55" "1" "" "0" "AOD-V-OSW0336" "")
(command "_.insert" "INCRA_vertice_V" "198888.06,8230715.92" "1" "" "0" "AOD-V-OSW0337" "")
(command "_.insert" "INCRA_vertice_V" "198888.61,8230714.89" "1" "" "0" "AOD-V-OSW0338" "")
(command "_.insert" "INCRA_vertice_V" "198889.75,8230713.51" "1" "" "0" "AOD-V-OSW0339" "")
(command "_.insert" "INCRA_vertice_V" "198890.93,8230712.4" "1" "" "0" "AOD-V-OSW0340" "")
(command "_.insert" "INCRA_vertice_V" "198891.8,8230711.71" "1" "" "0" "AOD-V-OSW0341" "")
(command "_.insert" "INCRA_vertice_V" "198893.07,8230710.91" "1" "" "0" "AOD-V-OSW0342" "")
(command "_.insert" "INCRA_vertice_V" "198894.59,8230709.91" "1" "" "0" "AOD-V-OSW0343" "")
(command "_.insert" "INCRA_vertice_V" "198896.45,8230708.56" "1" "" "0" "AOD-V-OSW0344" "")
(command "_.insert" "INCRA_vertice_V" "198898.37,8230706.85" "1" "" "0" "AOD-V-OSW0345" "")
(command "_.insert" "INCRA_vertice_V" "198900,8230705.32" "1" "" "0" "AOD-V-OSW0346" "")
(command "_.insert" "INCRA_vertice_V" "198901.14,8230704.34" "1" "" "0" "AOD-V-OSW0347" "")
(command "_.insert" "INCRA_vertice_V" "198902.08,8230703.88" "1" "" "0" "AOD-V-OSW0348" "")
(command "_.insert" "INCRA_vertice_V" "198903.21,8230703.59" "1" "" "0" "AOD-V-OSW0349" "")
(command "_.insert" "INCRA_vertice_V" "198904.73,8230703.25" "1" "" "0" "AOD-V-OSW0350" "")
(command "_.insert" "INCRA_vertice_V" "198906.31,8230702.82" "1" "" "0" "AOD-V-OSW0351" "")
(command "_.insert" "INCRA_vertice_V" "198907.48,8230702.93" "1" "" "0" "AOD-V-OSW0352" "")
(command "_.insert" "INCRA_vertice_V" "198909.44,8230703.13" "1" "" "0" "AOD-V-OSW0353" "")
(command "_.insert" "INCRA_vertice_V" "198910.45,8230703.32" "1" "" "0" "AOD-V-OSW0354" "")
(command "_.insert" "INCRA_vertice_V" "198911.45,8230703.61" "1" "" "0" "AOD-V-OSW0355" "")
(command "_.insert" "INCRA_vertice_V" "198912.17,8230703.64" "1" "" "0" "AOD-V-OSW0356" "")
(command "_.insert" "INCRA_vertice_V" "198913.39,8230703.02" "1" "" "0" "AOD-V-OSW0357" "")
(command "_.insert" "INCRA_vertice_V" "198914.41,8230702.28" "1" "" "0" "AOD-V-OSW0358" "")
(command "_.insert" "INCRA_vertice_V" "198916.43,8230700.42" "1" "" "0" "AOD-V-OSW0359" "")
(command "_.insert" "INCRA_vertice_V" "198917.46,8230699.17" "1" "" "0" "AOD-V-OSW0360" "")
(command "_.insert" "INCRA_vertice_V" "198918.65,8230697.33" "1" "" "0" "AOD-V-OSW0361" "")
(command "_.insert" "INCRA_vertice_V" "198919.7,8230695.09" "1" "" "0" "AOD-V-OSW0362" "")
(command "_.insert" "INCRA_vertice_V" "198920.78,8230693.37" "1" "" "0" "AOD-V-OSW0363" "")
(command "_.insert" "INCRA_vertice_V" "198921.87,8230692.03" "1" "" "0" "AOD-V-OSW0364" "")
(command "_.insert" "INCRA_vertice_V" "198923.4,8230690.8" "1" "" "0" "AOD-V-OSW0365" "")
(command "_.insert" "INCRA_vertice_V" "198925.88,8230689.45" "1" "" "0" "AOD-V-OSW0366" "")
(command "_.insert" "INCRA_vertice_V" "198927.36,8230688.86" "1" "" "0" "AOD-V-OSW0367" "")
(command "_.insert" "INCRA_vertice_V" "198928.89,8230687.96" "1" "" "0" "AOD-V-OSW0368" "")
(command "_.insert" "INCRA_vertice_V" "198930.14,8230686.56" "1" "" "0" "AOD-V-OSW0369" "")
(command "_.insert" "INCRA_vertice_V" "198931.27,8230685.01" "1" "" "0" "AOD-V-OSW0370" "")
(command "_.insert" "INCRA_vertice_V" "198932.3,8230683.84" "1" "" "0" "AOD-V-OSW0371" "")
(command "_.insert" "INCRA_vertice_V" "198934.32,8230681.96" "1" "" "0" "AOD-V-OSW0372" "")
(command "_.insert" "INCRA_vertice_V" "198936.18,8230680.54" "1" "" "0" "AOD-V-OSW0373" "")
(command "_.insert" "INCRA_vertice_V" "198937.25,8230679.65" "1" "" "0" "AOD-V-OSW0374" "")
(command "_.insert" "INCRA_vertice_V" "198938.05,8230678.77" "1" "" "0" "AOD-V-OSW0375" "")
(command "_.insert" "INCRA_vertice_V" "198938.74,8230678.29" "1" "" "0" "AOD-V-OSW0376" "")
(command "_.insert" "INCRA_vertice_V" "198940.05,8230677.9" "1" "" "0" "AOD-V-OSW0377" "")
(command "_.insert" "INCRA_vertice_V" "198940.9,8230677.8" "1" "" "0" "AOD-V-OSW0378" "")
(command "_.insert" "INCRA_vertice_V" "198941.9,8230677.39" "1" "" "0" "AOD-V-OSW0379" "")
(command "_.insert" "INCRA_vertice_V" "198942.96,8230676.36" "1" "" "0" "AOD-V-OSW0380" "")
(command "_.insert" "INCRA_vertice_V" "198943.85,8230674.87" "1" "" "0" "AOD-V-OSW0381" "")
(command "_.insert" "INCRA_vertice_V" "198944.31,8230674.12" "1" "" "0" "AOD-V-OSW0382" "")
(command "_.insert" "INCRA_vertice_V" "198945.27,8230673.39" "1" "" "0" "AOD-V-OSW0383" "")
(command "_.insert" "INCRA_vertice_V" "198946.65,8230672.78" "1" "" "0" "AOD-V-OSW0384" "")
(command "_.insert" "INCRA_vertice_V" "198947.98,8230672.54" "1" "" "0" "AOD-V-OSW0385" "")
(command "_.insert" "INCRA_vertice_V" "198949.25,8230672.17" "1" "" "0" "AOD-V-OSW0386" "")
(command "_.insert" "INCRA_vertice_V" "198950.39,8230671.33" "1" "" "0" "AOD-V-OSW0387" "")
(command "_.insert" "INCRA_vertice_V" "198952.13,8230669.67" "1" "" "0" "AOD-V-OSW0388" "")
(command "_.insert" "INCRA_vertice_V" "198953.95,8230667.53" "1" "" "0" "AOD-V-OSW0389" "")
(command "_.insert" "INCRA_vertice_V" "198955.15,8230665.98" "1" "" "0" "AOD-V-OSW0390" "")
(command "_.insert" "INCRA_vertice_V" "198955.8,8230665.17" "1" "" "0" "AOD-V-OSW0391" "")
(command "_.insert" "INCRA_vertice_V" "198956.54,8230664.55" "1" "" "0" "AOD-V-OSW0392" "")
(command "_.insert" "INCRA_vertice_V" "198957.4,8230664.04" "1" "" "0" "AOD-V-OSW0393" "")
(command "_.insert" "INCRA_vertice_V" "198958.44,8230663.39" "1" "" "0" "AOD-V-OSW0394" "")
(command "_.insert" "INCRA_vertice_V" "198959.77,8230662.54" "1" "" "0" "AOD-V-OSW0395" "")
(command "_.insert" "INCRA_vertice_V" "198960.64,8230661.96" "1" "" "0" "AOD-V-OSW0396" "")
(command "_.insert" "INCRA_vertice_V" "198961.44,8230661.32" "1" "" "0" "AOD-V-OSW0397" "")
(command "_.insert" "INCRA_vertice_V" "198961.8,8230660.96" "1" "" "0" "AOD-V-OSW0398" "")
(command "_.insert" "INCRA_vertice_V" "198962.52,8230659.96" "1" "" "0" "AOD-V-OSW0399" "")
(command "_.insert" "INCRA_vertice_V" "198963.08,8230658.82" "1" "" "0" "AOD-V-OSW0400" "")
(command "_.insert" "INCRA_vertice_V" "198963.84,8230657.05" "1" "" "0" "AOD-V-OSW0401" "")
(command "_.insert" "INCRA_vertice_V" "198964.13,8230656.48" "1" "" "0" "AOD-V-OSW0402" "")
(command "_.insert" "INCRA_vertice_V" "198966.18,8230653.13" "1" "" "0" "AOD-V-OSW0403" "")
(command "_.insert" "INCRA_vertice_V" "198967.98,8230649.55" "1" "" "0" "AOD-V-OSW0404" "")
(command "_.insert" "INCRA_vertice_V" "198967.55,8230645.54" "1" "" "0" "AOD-V-OSW0405" "")
(command "_.insert" "INCRA_vertice_V" "198968.02,8230642.07" "1" "" "0" "AOD-V-OSW0406" "")
(command "_.insert" "INCRA_vertice_V" "198969.46,8230639.05" "1" "" "0" "AOD-V-OSW0407" "")
(command "_.insert" "INCRA_vertice_V" "198972.68,8230635.76" "1" "" "0" "AOD-V-OSW0408" "")
(command "_.insert" "INCRA_vertice_V" "198973.88,8230634.55" "1" "" "0" "AOD-V-OSW0409" "")
(command "_.insert" "INCRA_vertice_V" "198976.25,8230632.93" "1" "" "0" "AOD-V-OSW0410" "")
(command "_.insert" "INCRA_vertice_V" "198978.93,8230629.73" "1" "" "0" "AOD-V-OSW0411" "")
(command "_.insert" "INCRA_vertice_V" "198981.78,8230628.13" "1" "" "0" "AOD-V-OSW0412" "")
(command "_.insert" "INCRA_vertice_V" "198984.54,8230627.01" "1" "" "0" "AOD-V-OSW0413" "")
(command "_.insert" "INCRA_vertice_V" "198986.54,8230625.62" "1" "" "0" "AOD-V-OSW0414" "")
(command "_.insert" "INCRA_vertice_V" "198991.75,8230623.51" "1" "" "0" "AOD-V-OSW0415" "")
(command "_.insert" "INCRA_vertice_V" "198993.8,8230620.68" "1" "" "0" "AOD-V-OSW0416" "")
(command "_.insert" "INCRA_vertice_V" "198998.12,8230617.52" "1" "" "0" "AOD-V-OSW0417" "")
(command "_.insert" "INCRA_vertice_V" "199003.97,8230614.7" "1" "" "0" "AOD-V-OSW0418" "")
(command "_.insert" "INCRA_vertice_V" "199006.57,8230614.17" "1" "" "0" "AOD-V-OSW0419" "")
(command "_.insert" "INCRA_vertice_V" "199011.57,8230616.61" "1" "" "0" "AOD-V-OSW0420" "")
(command "_.insert" "INCRA_vertice_V" "199016.15,8230617.42" "1" "" "0" "AOD-V-OSW0421" "")
(command "_.insert" "INCRA_vertice_V" "199020.44,8230614.77" "1" "" "0" "AOD-V-OSW0422" "")
(command "_.insert" "INCRA_vertice_V" "199027.1,8230612.67" "1" "" "0" "AOD-V-OSW0423" "")
(command "_.insert" "INCRA_vertice_V" "199033.94,8230612.23" "1" "" "0" "AOD-V-OSW0424" "")
(command "_.insert" "INCRA_vertice_V" "199039.19,8230608.11" "1" "" "0" "AOD-V-OSW0425" "")
(command "_.insert" "INCRA_vertice_V" "199043.21,8230603.07" "1" "" "0" "AOD-V-OSW0426" "")
(command "_.insert" "INCRA_vertice_V" "199046.58,8230598.32" "1" "" "0" "AOD-V-OSW0427" "")
(command "_.insert" "INCRA_vertice_V" "199051.1,8230596.41" "1" "" "0" "AOD-V-OSW0428" "")
(command "_.insert" "INCRA_vertice_V" "199052.76,8230592.64" "1" "" "0" "AOD-V-OSW0429" "")
(command "_.insert" "INCRA_vertice_V" "199053.7,8230587.59" "1" "" "0" "AOD-V-OSW0430" "")
(command "_.insert" "INCRA_vertice_V" "199055.23,8230584.69" "1" "" "0" "AOD-V-OSW0431" "")
(command "_.insert" "INCRA_vertice_V" "199055.35,8230581.52" "1" "" "0" "AOD-V-OSW0432" "")
(command "_.insert" "INCRA_vertice_V" "199054.73,8230578.14" "1" "" "0" "AOD-V-OSW0433" "")
(command "_.insert" "INCRA_vertice_V" "199056.98,8230574.01" "1" "" "0" "AOD-V-OSW0434" "")
(command "_.insert" "INCRA_vertice_V" "199060.72,8230569.8" "1" "" "0" "AOD-V-OSW0435" "")
(command "_.insert" "INCRA_vertice_V" "199061.77,8230566.36" "1" "" "0" "AOD-V-OSW0436" "")
(command "_.insert" "INCRA_vertice_V" "199064.57,8230566.12" "1" "" "0" "AOD-V-OSW0437" "")
(command "_.insert" "INCRA_vertice_V" "199068.63,8230565.27" "1" "" "0" "AOD-V-OSW0438" "")
(command "_.insert" "INCRA_vertice_V" "199074.36,8230560.58" "1" "" "0" "AOD-V-OSW0439" "")
(command "_.insert" "INCRA_vertice_V" "199078.3,8230557.66" "1" "" "0" "AOD-V-OSW0440" "")
(command "_.insert" "INCRA_vertice_V" "199088.69,8230554.94" "1" "" "0" "AOD-V-OSW0441" "")
(command "_.insert" "INCRA_vertice_V" "199092.59,8230550.47" "1" "" "0" "AOD-V-OSW0442" "")
(command "_.insert" "INCRA_vertice_V" "199097.31,8230552.25" "1" "" "0" "AOD-V-OSW0443" "")
(command "_.insert" "INCRA_vertice_V" "199103.88,8230550.28" "1" "" "0" "AOD-V-OSW0444" "")
(command "_.insert" "INCRA_vertice_V" "199109.37,8230548.4" "1" "" "0" "AOD-V-OSW0445" "")
(command "_.insert" "INCRA_vertice_V" "199110.76,8230546.21" "1" "" "0" "AOD-V-OSW0446" "")
(command "_.insert" "INCRA_vertice_V" "199111.15,8230546.14" "1" "" "0" "AOD-V-OSW0447" "")
(command "_.insert" "INCRA_vertice_V" "199203.54,8230690.81" "1" "" "0" "AOD-V-OSW0448" "")
(command "_.insert" "INCRA_vertice_V" "199249.56,8230763.71" "1" "" "0" "LBEL-M-0325" "")
(command "_.insert" "INCRA_vertice_V" "199318.33,8230873.7" "1" "" "0" "LBEL-M-0324" "")
(command "_.insert" "INCRA_vertice_V" "199283.14,8230890.45" "1" "" "0" "LBEL-P-0340" "")
(command "_.insert" "INCRA_vertice_V" "199246.69,8230912.47" "1" "" "0" "LBEL-P-0339" "")
(command "_.insert" "INCRA_vertice_V" "199227.23,8230922.92" "1" "" "0" "LBEL-P-0338" "")
(command "_.insert" "INCRA_vertice_V" "199201.24,8230936.93" "1" "" "0" "LBEL-P-0337" "")
(command "_.insert" "INCRA_vertice_V" "199177.6,8230949.13" "1" "" "0" "LBEL-P-0336" "")
(command "_.insert" "INCRA_vertice_V" "199169.46,8230954.68" "1" "" "0" "LBEL-P-0335" "")
(command "_.insert" "INCRA_vertice_V" "199112.39,8230967.02" "1" "" "0" "LBEL-M-0323" "")
(command "_.insert" "INCRA_vertice_V" "199110.31,8230967.37" "1" "" "0" "AOD-V-OSW0449" "")
(command "_.insert" "INCRA_vertice_V" "199108.21,8230967.64" "1" "" "0" "AOD-V-OSW0450" "")
(command "_.insert" "INCRA_vertice_V" "199104.02,8230966.31" "1" "" "0" "AOD-V-OSW0451" "")
(command "_.insert" "INCRA_vertice_V" "199099.68,8230964.35" "1" "" "0" "AOD-V-OSW0452" "")
(command "_.insert" "INCRA_vertice_V" "199097.48,8230962.98" "1" "" "0" "AOD-V-OSW0453" "")
(command "_.insert" "INCRA_vertice_V" "199094.95,8230963.07" "1" "" "0" "AOD-V-OSW0454" "")
(command "_.insert" "INCRA_vertice_V" "199092.88,8230964.23" "1" "" "0" "AOD-V-OSW0455" "")
(command "_.insert" "INCRA_vertice_V" "199090.95,8230965.76" "1" "" "0" "AOD-V-OSW0456" "")
(command "_.insert" "INCRA_vertice_V" "199088.03,8230968.42" "1" "" "0" "AOD-V-OSW0457" "")
(command "_.insert" "INCRA_vertice_V" "199086.5,8230970.64" "1" "" "0" "AOD-V-OSW0458" "")
(command "_.insert" "INCRA_vertice_V" "199083.98,8230972.4" "1" "" "0" "AOD-V-OSW0459" "")
(command "_.insert" "INCRA_vertice_V" "199081.7,8230973.84" "1" "" "0" "AOD-V-OSW0460" "")
(command "_.insert" "INCRA_vertice_V" "199073.87,8230975.09" "1" "" "0" "AOD-V-OSW0461" "")
(command "_.insert" "INCRA_vertice_V" "199071.37,8230974.9" "1" "" "0" "AOD-V-OSW0462" "")
(command "_.insert" "INCRA_vertice_V" "199068.71,8230974.76" "1" "" "0" "AOD-V-OSW0463" "")
(command "_.insert" "INCRA_vertice_V" "199067.16,8230974.32" "1" "" "0" "AOD-V-OSW0464" "")
(command "_.insert" "INCRA_vertice_V" "199066.22,8230974.13" "1" "" "0" "AOD-V-OSW0465" "")
(command "_.insert" "INCRA_vertice_V" "199065.26,8230974.52" "1" "" "0" "AOD-V-OSW0466" "")
(command "_.insert" "INCRA_vertice_V" "199064.97,8230974.75" "1" "" "0" "AOD-V-OSW0467" "")
(command "_.insert" "INCRA_vertice_V" "199063.75,8230975.67" "1" "" "0" "AOD-V-OSW0468" "")
(command "_.insert" "INCRA_vertice_V" "199062.32,8230975.94" "1" "" "0" "AOD-V-OSW0469" "")
(command "_.insert" "INCRA_vertice_V" "199061.25,8230975.74" "1" "" "0" "AOD-V-OSW0470" "")
(command "_.insert" "INCRA_vertice_V" "199060.19,8230976.4" "1" "" "0" "AOD-V-OSW0471" "")
(command "_.insert" "INCRA_vertice_V" "199058.68,8230977.33" "1" "" "0" "AOD-V-OSW0472" "")
(command "_.insert" "INCRA_vertice_V" "199056.33,8230978.47" "1" "" "0" "AOD-V-OSW0473" "")
(command "_.insert" "INCRA_vertice_V" "199053.99,8230978.81" "1" "" "0" "AOD-V-OSW0474" "")
(command "_.insert" "INCRA_vertice_V" "199049.83,8230978.19" "1" "" "0" "AOD-V-OSW0475" "")
(command "_.insert" "INCRA_vertice_V" "199047.08,8230977.38" "1" "" "0" "AOD-V-OSW0476" "")
(command "_.insert" "INCRA_vertice_V" "199044.59,8230976.98" "1" "" "0" "AOD-V-OSW0477" "")
(command "_.insert" "INCRA_vertice_V" "199043.1,8230977.09" "1" "" "0" "AOD-V-OSW0478" "")
(command "_.insert" "INCRA_vertice_V" "199040.95,8230977.75" "1" "" "0" "AOD-V-OSW0479" "")
(command "_.insert" "INCRA_vertice_V" "199038.97,8230978.45" "1" "" "0" "AOD-V-OSW0480" "")
(command "_.insert" "INCRA_vertice_V" "199036.7,8230979.53" "1" "" "0" "AOD-V-OSW0481" "")
(command "_.insert" "INCRA_vertice_V" "199034.64,8230981.26" "1" "" "0" "AOD-V-OSW0482" "")
(command "_.insert" "INCRA_vertice_V" "199033.63,8230981.85" "1" "" "0" "AOD-V-OSW0483" "")
(command "_.insert" "INCRA_vertice_V" "199030.73,8230982.81" "1" "" "0" "AOD-V-OSW0484" "")
(command "_.insert" "INCRA_vertice_V" "199027.93,8230983.54" "1" "" "0" "AOD-V-OSW0485" "")
(command "_.insert" "INCRA_vertice_V" "199026.17,8230983.83" "1" "" "0" "AOD-V-OSW0486" "")
(command "_.insert" "INCRA_vertice_V" "199024.01,8230984.71" "1" "" "0" "AOD-V-OSW0487" "")
(command "_.insert" "INCRA_vertice_V" "199021.48,8230986.62" "1" "" "0" "AOD-V-OSW0488" "")
(command "_.insert" "INCRA_vertice_V" "199018.77,8230989.7" "1" "" "0" "AOD-V-OSW0489" "")
(command "_.insert" "INCRA_vertice_V" "199015.65,8230994.08" "1" "" "0" "AOD-V-OSW0490" "")
(command "_.insert" "INCRA_vertice_V" "199014.74,8230995.94" "1" "" "0" "AOD-V-OSW0491" "")
(command "_.insert" "INCRA_vertice_V" "199014.48,8230997.78" "1" "" "0" "AOD-V-OSW0492" "")
(command "_.insert" "INCRA_vertice_V" "199014.06,8231000.57" "1" "" "0" "AOD-V-OSW0493" "")
(command "_.insert" "INCRA_vertice_V" "199013.08,8231003.79" "1" "" "0" "AOD-V-OSW0494" "")
(command "_.insert" "INCRA_vertice_V" "199012.07,8231005.95" "1" "" "0" "AOD-V-OSW0495" "")
(command "_.insert" "INCRA_vertice_V" "199009.9,8231007.07" "1" "" "0" "AOD-V-OSW0496" "")
(command "_.insert" "INCRA_vertice_V" "199008.07,8231008.67" "1" "" "0" "AOD-V-OSW0497" "")
(command "_.insert" "INCRA_vertice_V" "199006.8,8231010.69" "1" "" "0" "AOD-V-OSW0498" "")
(command "_.insert" "INCRA_vertice_V" "199005.57,8231014.17" "1" "" "0" "AOD-V-OSW0499" "")
(command "_.insert" "INCRA_vertice_V" "199004.18,8231016.56" "1" "" "0" "AOD-V-OSW0500" "")
(command "_.insert" "INCRA_vertice_V" "199002.65,8231019.11" "1" "" "0" "AOD-V-OSW0501" "")
(command "_.insert" "INCRA_vertice_V" "198999.57,8231022.43" "1" "" "0" "AOD-V-OSW0502" "")
(command "_.insert" "INCRA_vertice_V" "198997.77,8231024.9" "1" "" "0" "AOD-V-OSW0503" "")
(command "_.insert" "INCRA_vertice_V" "198997.55,8231026.15" "1" "" "0" "AOD-V-OSW0504" "")
(command "_.insert" "INCRA_vertice_V" "198997.46,8231028.41" "1" "" "0" "AOD-V-OSW0505" "")
(command "_.insert" "INCRA_vertice_V" "198996.11,8231029.7" "1" "" "0" "AOD-V-OSW0506" "")
(command "_.insert" "INCRA_vertice_V" "198995.14,8231030.46" "1" "" "0" "AOD-V-OSW0507" "")
(command "_.insert" "INCRA_vertice_V" "198994.21,8231032.38" "1" "" "0" "AOD-V-OSW0508" "")
(command "_.insert" "INCRA_vertice_V" "198993.48,8231033.28" "1" "" "0" "AOD-V-OSW0509" "")
(command "_.insert" "INCRA_vertice_V" "198992.29,8231034.51" "1" "" "0" "AOD-V-OSW0510" "")
(command "_.insert" "INCRA_vertice_V" "198991.52,8231036.07" "1" "" "0" "AOD-V-OSW0511" "")
(command "_.insert" "INCRA_vertice_V" "198990.56,8231038.98" "1" "" "0" "AOD-V-OSW0512" "")
(command "_.insert" "INCRA_vertice_V" "198989.74,8231043.25" "1" "" "0" "AOD-V-OSW0513" "")
(command "_.insert" "INCRA_vertice_V" "198990.03,8231044.8" "1" "" "0" "AOD-V-OSW0514" "")
(command "_.insert" "INCRA_vertice_V" "198990.08,8231046.8" "1" "" "0" "AOD-V-OSW0515" "")
(command "_.insert" "INCRA_vertice_V" "198989.97,8231049.84" "1" "" "0" "AOD-V-OSW0516" "")
(command "_.insert" "INCRA_vertice_V" "198989.7,8231050.61" "1" "" "0" "AOD-V-OSW0517" "")
(command "_.insert" "INCRA_vertice_V" "198988.79,8231051.76" "1" "" "0" "AOD-V-OSW0518" "")
(command "_.insert" "INCRA_vertice_V" "198987.61,8231053.09" "1" "" "0" "AOD-V-OSW0519" "")
(command "_.insert" "INCRA_vertice_V" "198987.23,8231053.67" "1" "" "0" "AOD-V-OSW0520" "")
(command "_.insert" "INCRA_vertice_V" "198987.03,8231054.55" "1" "" "0" "AOD-V-OSW0521" "")
(command "_.insert" "INCRA_vertice_V" "198986.59,8231055.95" "1" "" "0" "AOD-V-OSW0522" "")
(command "_.insert" "INCRA_vertice_V" "198985.73,8231057.73" "1" "" "0" "AOD-V-OSW0523" "")
(command "_.insert" "INCRA_vertice_V" "198983.64,8231060.98" "1" "" "0" "AOD-V-OSW0524" "")
(command "_.insert" "INCRA_vertice_V" "198981.93,8231063.63" "1" "" "0" "AOD-V-OSW0525" "")
(command "_.insert" "INCRA_vertice_V" "198980.32,8231066.11" "1" "" "0" "AOD-V-OSW0526" "")
(command "_.insert" "INCRA_vertice_V" "198978.66,8231068.77" "1" "" "0" "AOD-V-OSW0527" "")
(command "_.insert" "INCRA_vertice_V" "198977.09,8231070.73" "1" "" "0" "AOD-V-OSW0528" "")
(command "_.insert" "INCRA_vertice_V" "198976.34,8231071.66" "1" "" "0" "AOD-V-OSW0529" "")
(command "_.insert" "INCRA_vertice_V" "198976.17,8231072.56" "1" "" "0" "AOD-V-OSW0530" "")
(command "_.insert" "INCRA_vertice_V" "198976.33,8231073.49" "1" "" "0" "AOD-V-OSW0531" "")
(command "_.insert" "INCRA_vertice_V" "198976.58,8231074.87" "1" "" "0" "AOD-V-OSW0532" "")
(command "_.insert" "INCRA_vertice_V" "198976.53,8231075.92" "1" "" "0" "AOD-V-OSW0533" "")
(command "_.insert" "INCRA_vertice_V" "198976.29,8231076.47" "1" "" "0" "AOD-V-OSW0534" "")
(command "_.insert" "INCRA_vertice_V" "198975.62,8231076.86" "1" "" "0" "AOD-V-OSW0535" "")
(command "_.insert" "INCRA_vertice_V" "198974.93,8231077.31" "1" "" "0" "AOD-V-OSW0536" "")
(command "_.insert" "INCRA_vertice_V" "198973.53,8231078.51" "1" "" "0" "AOD-V-OSW0537" "")
(command "_.insert" "INCRA_vertice_V" "198972.6,8231079.64" "1" "" "0" "AOD-V-OSW0538" "")
(command "_.insert" "INCRA_vertice_V" "198971.49,8231081.58" "1" "" "0" "AOD-V-OSW0539" "")
(command "_.insert" "INCRA_vertice_V" "198970.45,8231083.65" "1" "" "0" "AOD-V-OSW0540" "")
(command "_.insert" "INCRA_vertice_V" "198969.7,8231085.64" "1" "" "0" "AOD-V-OSW0541" "")
(command "_.insert" "INCRA_vertice_V" "198969.22,8231087.54" "1" "" "0" "AOD-V-OSW0542" "")
(command "_.insert" "INCRA_vertice_V" "198968.8,8231088.77" "1" "" "0" "AOD-V-OSW0543" "")
(command "_.insert" "INCRA_vertice_V" "198968.77,8231089.33" "1" "" "0" "AOD-V-OSW0544" "")
(command "_.insert" "INCRA_vertice_V" "198969.38,8231091.11" "1" "" "0" "AOD-V-OSW0545" "")
(command "_.insert" "INCRA_vertice_V" "198969.89,8231092.24" "1" "" "0" "AOD-V-OSW0546" "")
(command "_.insert" "INCRA_vertice_V" "198970,8231093.5" "1" "" "0" "AOD-V-OSW0547" "")
(command "_.insert" "INCRA_vertice_V" "198969.68,8231094.73" "1" "" "0" "AOD-V-OSW0548" "")
(command "_.insert" "INCRA_vertice_V" "198968.92,8231095.97" "1" "" "0" "AOD-V-OSW0549" "")
(command "_.insert" "INCRA_vertice_V" "198967.73,8231097.42" "1" "" "0" "AOD-V-OSW0550" "")
(command "_.insert" "INCRA_vertice_V" "198966.7,8231098.86" "1" "" "0" "AOD-V-OSW0551" "")
(command "_.insert" "INCRA_vertice_V" "198966.13,8231100.13" "1" "" "0" "AOD-V-OSW0552" "")
(command "_.insert" "INCRA_vertice_V" "198966.06,8231101.56" "1" "" "0" "AOD-V-OSW0553" "")
(command "_.insert" "INCRA_vertice_V" "198966.44,8231102.82" "1" "" "0" "AOD-V-OSW0554" "")
(command "_.insert" "INCRA_vertice_V" "198967.42,8231104.46" "1" "" "0" "AOD-V-OSW0555" "")
(command "_.insert" "INCRA_vertice_V" "198968.21,8231105.08" "1" "" "0" "AOD-V-OSW0556" "")
(command "_.insert" "INCRA_vertice_V" "198969.43,8231105.88" "1" "" "0" "AOD-V-OSW0557" "")
(command "_.insert" "INCRA_vertice_V" "198970.49,8231106.8" "1" "" "0" "AOD-V-OSW0558" "")
(command "_.insert" "INCRA_vertice_V" "198970.79,8231107.31" "1" "" "0" "AOD-V-OSW0559" "")
(command "_.insert" "INCRA_vertice_V" "198971.29,8231108.43" "1" "" "0" "AOD-V-OSW0560" "")
(command "_.insert" "INCRA_vertice_V" "198972.21,8231109.92" "1" "" "0" "AOD-V-OSW0561" "")
(command "_.insert" "INCRA_vertice_V" "198972.55,8231110.57" "1" "" "0" "AOD-V-OSW0562" "")
(command "_.insert" "INCRA_vertice_V" "198972.87,8231111.72" "1" "" "0" "AOD-V-OSW0563" "")
(command "_.insert" "INCRA_vertice_V" "198973.14,8231112.79" "1" "" "0" "AOD-V-OSW0564" "")
(command "_.insert" "INCRA_vertice_V" "198973.19,8231113.44" "1" "" "0" "AOD-V-OSW0565" "")
(command "_.insert" "INCRA_vertice_V" "198973.09,8231114.06" "1" "" "0" "AOD-V-OSW0566" "")
(command "_.insert" "INCRA_vertice_V" "198972.89,8231114.61" "1" "" "0" "AOD-V-OSW0567" "")
(command "_.insert" "INCRA_vertice_V" "198972.68,8231114.9" "1" "" "0" "AOD-V-OSW0568" "")
(command "_.insert" "INCRA_vertice_V" "198972.23,8231115.24" "1" "" "0" "AOD-V-OSW0569" "")
(command "_.insert" "INCRA_vertice_V" "198971.99,8231115.55" "1" "" "0" "AOD-V-OSW0570" "")
(command "_.insert" "INCRA_vertice_V" "198971.5,8231116" "1" "" "0" "AOD-V-OSW0571" "")
(command "_.insert" "INCRA_vertice_V" "198971.3,8231116.39" "1" "" "0" "AOD-V-OSW0572" "")
(command "_.insert" "INCRA_vertice_V" "198971.16,8231116.84" "1" "" "0" "AOD-V-OSW0573" "")
(command "_.insert" "INCRA_vertice_V" "198970.83,8231117.71" "1" "" "0" "AOD-V-OSW0574" "")
(command "_.insert" "INCRA_vertice_V" "198970.53,8231118.14" "1" "" "0" "AOD-V-OSW0575" "")
(command "_.insert" "INCRA_vertice_V" "198969.4,8231119.37" "1" "" "0" "AOD-V-OSW0576" "")
(command "_.insert" "INCRA_vertice_V" "198968.45,8231120.08" "1" "" "0" "AOD-V-OSW0577" "")
(command "_.insert" "INCRA_vertice_V" "198967.79,8231120.39" "1" "" "0" "AOD-V-OSW0578" "")
(command "_.insert" "INCRA_vertice_V" "198967.26,8231120.57" "1" "" "0" "AOD-V-OSW0579" "")
(command "_.insert" "INCRA_vertice_V" "198987.86,8231145.3" "1" "" "0" "AOD-M-OSW0022" "")
(command "_.insert" "INCRA_vertice_V" "199010.97,8231165.99" "1" "" "0" "AOD-M-OSW0023" "")
(command "_.insert" "INCRA_vertice_V" "199044.09,8231194.2" "1" "" "0" "AOD-M-OSW0024" "")
(command "_.insert" "INCRA_vertice_V" "199008.28,8231226.37" "1" "" "0" "AOD-M-OSW0025" "")
(command "_.insert" "INCRA_vertice_V" "199074.69,8231263.83" "1" "" "0" "AOD-M-OSW0026" "")
(command "_.insert" "INCRA_vertice_V" "199071.67,8231264.07" "1" "" "0" "AOD-M-OSW0027" "")
(command "_.insert" "INCRA_vertice_V" "199068.91,8231264.8" "1" "" "0" "AOD-M-OSW0028" "")
(command "_.insert" "INCRA_vertice_V" "199061.62,8231273.68" "1" "" "0" "AOD-M-OSW0029" "")
(command "_.insert" "INCRA_vertice_V" "199058.55,8231275.42" "1" "" "0" "AOD-M-OSW0030" "")
(command "_.insert" "INCRA_vertice_V" "199053.18,8231274.93" "1" "" "0" "AOD-M-OSW0031" "")
(command "_.insert" "INCRA_vertice_V" "199049.91,8231275.4" "1" "" "0" "AOD-M-OSW0032" "")
(command "_.insert" "INCRA_vertice_V" "199039.35,8231291.71" "1" "" "0" "AOD-M-OSW0033" "")
(command "_.insert" "INCRA_vertice_V" "199030.27,8231299.5" "1" "" "0" "AOD-M-OSW0034" "")
(command "_.insert" "INCRA_vertice_V" "199025.14,8231310.08" "1" "" "0" "AOD-M-OSW0035" "")
(command "_.insert" "INCRA_vertice_V" "199031.79,8231324.26" "1" "" "0" "AOD-M-OSW0036" "")
(command "_.insert" "INCRA_vertice_V" "199023.78,8231337.34" "1" "" "0" "AOD-M-OSW0037" "")
(command "_.insert" "INCRA_vertice_V" "199019.18,8231350.77" "1" "" "0" "AOD-M-OSW0038" "")
(command "_.insert" "INCRA_vertice_V" "199016.96,8231358.89" "1" "" "0" "AOD-M-OSW0039" "")
(command "_.insert" "INCRA_vertice_V" "199014.75,8231361.9" "1" "" "0" "AOD-M-OSW0040" "")
(command "_.insert" "INCRA_vertice_V" "199014.37,8231370.5" "1" "" "0" "AOD-M-OSW0041" "")
(command "_.insert" "INCRA_vertice_V" "199003.87,8231403" "1" "" "0" "AOD-M-OSW0042" "")
(command "_.insert" "INCRA_vertice_V" "198993.12,8231443.88" "1" "" "0" "AOD-M-OSW0043" "")
(command "_.insert" "INCRA_vertice_V" "198980.88,8231490.13" "1" "" "0" "AOD-M-OSW0044" "")
(command "_.insert" "INCRA_vertice_V" "198965.74,8231547.32" "1" "" "0" "AOD-M-OSW0045" "")
(command "_.insert" "INCRA_vertice_V" "198959.9,8231573.23" "1" "" "0" "AOD-M-OSW0046" "")
(command "_.insert" "INCRA_vertice_V" "198975.59,8231579.87" "1" "" "0" "AOD-M-OSW0047" "")
(command "_.insert" "INCRA_vertice_V" "199016.32,8231618.31" "1" "" "0" "AOD-M-OSW0048" "")
(command "_.insert" "INCRA_vertice_V" "199020.18,8231622.76" "1" "" "0" "AOD-M-OSW0049" "")
(command "_.insert" "INCRA_vertice_V" "199099.75,8231709.92" "1" "" "0" "AOD-M-OSW0050" "")
(command "_.insert" "INCRA_vertice_V" "199108.5,8231666.1" "1" "" "0" "AOD-M-OSW0051" "")
(command "_.insert" "INCRA_vertice_V" "199123.52,8231651.64" "1" "" "0" "AOD-M-OSW0052" "")
(command "_.insert" "INCRA_vertice_V" "199159.49,8231639.93" "1" "" "0" "AOD-M-OSW0053" "")
(command "_.insert" "INCRA_vertice_V" "199183.7,8231633.73" "1" "" "0" "AOD-M-OSW0054" "")
(command "_.insert" "INCRA_vertice_V" "199241.1,8231618.67" "1" "" "0" "AOD-M-OSW0055" "")
(command "_.insert" "INCRA_vertice_V" "199259.54,8231619.25" "1" "" "0" "AOD-M-OSW0056" "")
(command "_.insert" "INCRA_vertice_V" "199274.2,8231671.92" "1" "" "0" "AOD-M-OSW0057" "")
(command "_.insert" "INCRA_vertice_V" "199293.28,8231739.35" "1" "" "0" "AOD-M-OSW0058" "")
(command "_.insert" "INCRA_vertice_V" "199295.84,8231749.34" "1" "" "0" "AOD-M-OSW0059" "")
(command "_.insert" "INCRA_vertice_V" "199344.14,8231725.13" "1" "" "0" "AOD-M-OSW0060" "")
(command "_.insert" "INCRA_vertice_V" "199375.87,8231708.78" "1" "" "0" "AOD-M-OSW0061" "")
(command "_.insert" "INCRA_vertice_V" "199408.68,8231691.18" "1" "" "0" "AOD-M-OSW0062" "")
(command "_.insert" "INCRA_vertice_V" "199434.2,8231676.73" "1" "" "0" "AOD-M-OSW0063" "")
(command "_.insert" "INCRA_vertice_V" "199515.95,8231634.3" "1" "" "0" "AOD-M-OSW0064" "")
(command "_.insert" "INCRA_vertice_V" "199536.1,8231626.37" "1" "" "0" "AOD-M-OSW0065" "")
(command "_.insert" "INCRA_vertice_V" "199582.42,8231627.01" "1" "" "0" "AOD-M-OSW0066" "")
(command "_.insert" "INCRA_vertice_V" "199615.85,8231616.31" "1" "" "0" "AOD-M-OSW0067" "")
(command "_.insert" "INCRA_vertice_V" "199689.21,8231592.87" "1" "" "0" "AOD-M-OSW0068" "")
(command "_.insert" "INCRA_vertice_V" "199721.48,8231561.57" "1" "" "0" "AOD-M-OSW0069" "")
(command "_.insert" "INCRA_vertice_V" "199743.31,8231634.38" "1" "" "0" "AOD-M-OSW0070" "")
(command "_.insert" "INCRA_vertice_V" "199749.84,8231655.78" "1" "" "0" "AOD-M-OSW0071" "")
(command "_.insert" "INCRA_vertice_V" "199764.66,8231704.65" "1" "" "0" "AOD-M-OSW0072" "")
(command "_.insert" "INCRA_vertice_V" "199793.92,8231789.34" "1" "" "0" "AOD-M-OSW0073" "")
(command "_.insert" "INCRA_vertice_V" "199800.02,8231807.33" "1" "" "0" "AOD-M-OSW0074" "")
(command "_.insert" "INCRA_vertice_V" "199807.03,8231828.01" "1" "" "0" "AOD-M-OSW0075" "")
(command "_.insert" "INCRA_vertice_V" "199816.81,8231856.81" "1" "" "0" "AOD-M-OSW0076" "")
(command "_.insert" "INCRA_vertice_V" "199826.9,8231886.29" "1" "" "0" "AOD-M-OSW0077" "")
(command "_.insert" "INCRA_vertice_V" "199840.88,8231926.43" "1" "" "0" "AOD-M-OSW0078" "")
(command "_.insert" "INCRA_vertice_V" "199857.01,8231974.2" "1" "" "0" "AOD-M-OSW0079" "")
(command "_.insert" "INCRA_vertice_V" "199878.57,8232038.03" "1" "" "0" "AOD-V-OSW0580" "")
(command "_.insert" "INCRA_vertice_V" "199884.03,8232038.45" "1" "" "0" "AOD-V-OSW0581" "")
(command "_.insert" "INCRA_vertice_V" "199940.3,8232048.79" "1" "" "0" "AOD-V-OSW0582" "")
(setvar "clayer" oldlayer)
(princ)
)
(princ "\nDigite 'botavertice' para iniciar")
