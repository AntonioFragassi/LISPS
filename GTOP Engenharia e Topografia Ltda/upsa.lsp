;; Coloca os blocos segundo a descrição 
(defun c:UPSA(/)
(princ "********* Espere um pouco - processando dados  ***********")
(setq olcmdecho (getvar "cmdecho"))
(setvar "cmdecho" 0)
(command "_.insert" "INCRA_vertice_M" "196070.42,8264743.29" 1 "" "" "A0D-M-1890")
(command "_.insert" "INCRA_vertice_M" "196088.94,8264719.96" 1 "" "" "A0D-M-1891")
(command "_.insert" "INCRA_vertice_M" "196100.04,8264709.7" 1 "" "" "A0D-M-1892")
(command "_.insert" "INCRA_vertice_M" "196101.75,8264706.64" 1 "" "" "A0D-M-1893")
(command "_.insert" "INCRA_vertice_M" "196050.7,8264606.05" 1 "" "" "A0D-M-1898")
(command "_.insert" "INCRA_vertice_M" "196059.43,8264815.77" 1 "" "" "A0D-M-2489")
(command "_.insert" "INCRA_vertice_M" "196059.99,8264800.94" 1 "" "" "A0D-M-2490")
(command "_.insert" "INCRA_vertice_M" "196060.26,8264778.8" 1 "" "" "A0D-M-2491")
(command "_.insert" "INCRA_vertice_M" "196101.69,8264690" 1 "" "" "A0D-M-2496")
(command "_.insert" "INCRA_vertice_M" "196101.95,8264666.99" 1 "" "" "A0D-M-2497")
(command "_.insert" "INCRA_vertice_M" "196070.41,8264662.25" 1 "" "" "A0D-M-2498")
(command "_.insert" "INCRA_vertice_M" "196058.72,8264660.7" 1 "" "" "A0D-M-2499")
(command "_.insert" "INCRA_vertice_M" "196057.6,8264646.66" 1 "" "" "A0D-M-2500")
(command "_.insert" "INCRA_vertice_M" "196055.54,8264627.27" 1 "" "" "A0D-M-2501")
(command "_.insert" "INCRA_vertice_M" "196041.32,8264577.93" 1 "" "" "A0D-M-2503")
(command "_.insert" "INCRA_vertice_M" "196032.46,8264550.11" 1 "" "" "A0D-M-2504")
(command "_.insert" "INCRA_vertice_M" "196008.71,8264552.68" 1 "" "" "A0D-M-2505")
(command "_.insert" "INCRA_vertice_M" "195997.64,8264553.8" 1 "" "" "A0D-M-2506")
(command "_.insert" "INCRA_vertice_M" "195997.1,8264548.73" 1 "" "" "A0D-M-2507")
(command "_.insert" "INCRA_vertice_M" "195968.89,8264551.85" 1 "" "" "A0D-M-2508")
(command "_.insert" "INCRA_vertice_M" "195964.84,8264563.85" 1 "" "" "A0D-M-2510")
(command "_.insert" "INCRA_vertice_M" "195955.92,8264565.88" 1 "" "" "A0D-M-2511")
(command "_.insert" "INCRA_vertice_M" "195956.25,8264567.55" 1 "" "" "A0D-M-2512")
(command "_.insert" "INCRA_vertice_M" "195957.16,8264571.65" 1 "" "" "A0D-M-2513")
(command "_.insert" "INCRA_vertice_M" "195958.1,8264575.68" 1 "" "" "A0D-M-2514")
(command "_.insert" "INCRA_vertice_M" "195956.89,8264576" 1 "" "" "A0D-M-2515")
(command "_.insert" "INCRA_vertice_M" "195941.32,8264579.47" 1 "" "" "A0D-M-2516")
(command "_.insert" "INCRA_vertice_M" "195923.4,8264583.34" 1 "" "" "A0D-M-2517")
(command "_.insert" "INCRA_vertice_M" "195923.6,8264590.19" 1 "" "" "A0D-M-2518")
(command "_.insert" "INCRA_vertice_M" "195932.7,8264603.78" 1 "" "" "A0D-M-2519")
(command "_.insert" "INCRA_vertice_M" "195930.6,8264610.89" 1 "" "" "A0D-M-2520")
(command "_.insert" "INCRA_vertice_M" "195944.99,8264614.02" 1 "" "" "A0D-M-2521")
(command "_.insert" "INCRA_vertice_M" "195956.58,8264628.5" 1 "" "" "A0D-M-2522")
(command "_.insert" "INCRA_vertice_M" "195951.31,8264644.18" 1 "" "" "A0D-M-2523")
(command "_.insert" "INCRA_vertice_M" "195946.37,8264658.37" 1 "" "" "A0D-M-2524")
(command "_.insert" "INCRA_vertice_M" "195932.39,8264653.74" 1 "" "" "A0D-M-2525")
(command "_.insert" "INCRA_vertice_M" "195914.87,8264647.84" 1 "" "" "A0D-M-2526")
(command "_.insert" "INCRA_vertice_M" "195911.29,8264646.59" 1 "" "" "A0D-M-2527")
(command "_.insert" "INCRA_vertice_M" "195909.35,8264645.94" 1 "" "" "A0D-M-2528")
(command "_.insert" "INCRA_vertice_M" "195908.43,8264645.63" 1 "" "" "A0D-M-2529")
(command "_.insert" "INCRA_vertice_M" "195888.75,8264638.75" 1 "" "" "A0D-M-2530")
(command "_.insert" "INCRA_vertice_M" "195861.12,8264629.52" 1 "" "" "A0D-M-2531")
(command "_.insert" "INCRA_vertice_M" "195852.52,8264654.95" 1 "" "" "A0D-M-2532")
(command "_.insert" "INCRA_vertice_M" "195844.81,8264677.55" 1 "" "" "A0D-M-2533")
(command "_.insert" "INCRA_vertice_M" "195813.94,8264667.25" 1 "" "" "A0D-M-2534")
(command "_.insert" "INCRA_vertice_M" "195807.65,8264689.64" 1 "" "" "A0D-M-2535")
(command "_.insert" "INCRA_vertice_M" "195798.71,8264722.53" 1 "" "" "A0D-M-2536")
(command "_.insert" "INCRA_vertice_M" "195788.79,8264754.83" 1 "" "" "A0D-M-2537")
(command "_.insert" "INCRA_vertice_M" "195782.38,8264775.42" 1 "" "" "A0D-M-2538")
(command "_.insert" "INCRA_vertice_M" "195777.94,8264789.31" 1 "" "" "A0D-M-2539")
(command "_.insert" "INCRA_vertice_M" "195963.54,8264552.3" 1 "" "" "A0D-M-6000")
(command "_.insert" "INCRA_vertice_M" "196055.39,8264848.19" 1 "" "" "A0D-V-5132")
(command "_.insert" "INCRA_vertice_M" "195960.12,8264617.3" 1 "" "" "A0D-V-5134")
(command "_.insert" "INCRA_vertice_M" "195771.79,8264807.76" 1 "" "" "A0D-V-5135")
(command "_.insert" "INCRA_vertice_M" "195920.46,8264828.96" 1 "" "" "A0D-V-5136")
(command "_.insert" "INCRA_vertice_M" "196012.31,8264737" 1 "" "" "A0D-V-5149")
(command "_.insert" "INCRA_vertice_M" "196062.4,8264771.3" 1 "" "" "A0D-V-8001")
(setvar "cmdecho" olcmdecho)
(setvar "clayer" oldlayer)
(princ)
)
(princ "\nDigite 'UPSA' para iniciar")
