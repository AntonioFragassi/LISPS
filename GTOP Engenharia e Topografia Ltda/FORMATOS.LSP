(defun C:FOLHA (/ h formato escala p1 p2)
 	(setq formato (getint "\nTamanho da Folha (0 1 2 3 4): "))
    (setq escala (getreal "Escala do desenho: "))
    (setq p1( getpoint "\nClique em um ponto: "))
 	(cond
		((= formato 0) (setq h '(1189 841 0)))
       	((= formato 1) (setq h '(841 594 0)))
       	((= formato 2) (setq h '(594 420 0)))
       	((= formato 3) (setq h '(420 297 0)))
       	((= formato 4) (setq h '(297 210 0)))
 	   )
 	(setq fator (/ escala 1000))
    (setq p2 (cal "p1+h*fator"))
    (command "_.rectang" p1 p2 "")
)
(princ "\nDigite 'folha' para iniciar")
