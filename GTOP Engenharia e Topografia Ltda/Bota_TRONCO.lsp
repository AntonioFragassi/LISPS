;; Coloca o diâmetro dos troncos segundo a descrição 

(defun c:TRONCO( / olcmdecho oldlayer escala Conjunto_INSERT Comp_Conjunto Objeto ponto lista  Attn Attv diam)
(princ "********* Espere um pouco - processando dados  ***********")
(setq olcmdecho (getvar "cmdecho"))
(setvar "cmdecho" 0) 
(setq oldlayer (getvar "clayer"))
(setq escala (getreal "Escala do desenho: "))
(setq escala (/ escala 1000.0))
(setq Conjunto_INSERT (ssget '((0 . "INSERT"))))
(if Conjunto_INSERT ;; primeiro if
     (progn 
	(setq Comp_Conjunto (sslength Conjunto_INSERT))
	(while (> Comp_Conjunto 0) ;; primeiro while
	      (setq Comp_Conjunto (1- Comp_Conjunto))
	      (setq Objeto (ssname Conjunto_INSERT  Comp_Conjunto))
                   (setq ponto (cdr (assoc 10 (entget Objeto))))
 	      (while (/= (cdr (assoc 0 (entget OBJETO))) "SEQEND")
        		(setq OBJETO (entnext OBJETO))
  		(setq lista (entget OBJETO))
       		(setq Attn (cdr (assoc 2 lista)))
  		(setq Attv (cdr (assoc 1 lista)))
        		(if (= Attn "DESC")
	                  (progn
		                (setq desc (substr Attv 4 ))
		        	   (setq Attv (substr Attv 4 7))
                                         (cond

		(( = Attv "10" ) (progn (command "_.layer" "m" "TRONCO" "")(command "_.insert" "tronco_010.dwg" ponto escala "" "0" "")))			
(( = Attv "20" ) (progn (command "_.layer" "m" "TRONCO" "")(command "_.insert" "tronco_020.dwg" ponto escala "" "0" "")))
				(( = Attv "30" ) (progn (command "_.layer" "m" "TRONCO" "")(command "_.insert" "tronco_030.dwg" ponto escala "" "0" "")))
(( = Attv "40" ) (progn (command "_.layer" "m" "TRONCO" "")(command "_.insert" "tronco_040.dwg" ponto escala "" "0" "")))
				(( = Attv "50" ) (progn (command "_.layer" "m" "TRONCO" "")(command "_.insert" "tronco_050.dwg" ponto escala "" "0" "")))
(( = Attv "60" ) (progn (command "_.layer" "m" "TRONCO" "")(command "_.insert" "tronco_060.dwg" ponto escala "" "0" "")))
				(( = Attv "70" ) (progn (command "_.layer" "m" "TRONCO" "")(command "_.insert" "tronco_070.dwg" ponto escala "" "0" "")))
				(( = Attv "80" ) (progn (command "_.layer" "m" "TRONCO" "")(command "_.insert" "tronco_080.dwg" ponto escala "" "0" "")))
(( = Attv "90" ) (progn (command "_.layer" "m" "TRONCO" "")(command "_.insert" "tronco_090.dwg" ponto escala "" "0" "")))
				(( = Attv "100" ) (progn (command "_.layer" "m" "TRONCO" "")(command "_.insert" "tronco_100.dwg" ponto escala "" "0" "")))
(( = Attv "110" ) (progn (command "_.layer" "m" "TRONCO" "")(command "_.insert" "tronco_110.dwg" ponto escala "" "0" "")))
(( = Attv "120" ) (progn (command "_.layer" "m" "TRONCO" "")(command "_.insert" "tronco_120.dwg" ponto escala "" "0" "")))
(( = Attv "130" ) (progn (command "_.layer" "m" "TRONCO" "")(command "_.insert" "tronco_130.dwg" ponto escala "" "0" "")))
(( = Attv "140" ) (progn (command "_.layer" "m" "TRONCO" "")(command "_.insert" "tronco_140.dwg" ponto escala "" "0" "")))
				(( = Attv "150" ) (progn (command "_.layer" "m" "TRONCO" "")(command "_.insert" "tronco_150.dwg" ponto escala "" "0" "")))
(( = Attv "160" ) (progn (command "_.layer" "m" "TRONCO" "")(command "_.insert" "tronco_160.dwg" ponto escala "" "0" "")))
(( = Attv "170" ) (progn (command "_.layer" "m" "TRONCO" "")(command "_.insert" "tronco_170.dwg" ponto escala "" "0" "")))
(( = Attv "180" ) (progn (command "_.layer" "m" "TRONCO" "")(command "_.insert" "tronco_180.dwg" ponto escala "" "0" "")))
(( = Attv "190" ) (progn (command "_.layer" "m" "TRONCO" "")(command "_.insert" "tronco_190.dwg" ponto escala "" "0" "")))
				(( = Attv "200" ) (progn (command "_.layer" "m" "TRONCO" "")(command "_.insert" "tronco_200.dwg" ponto escala "" "0" "")))
(( = Attv "210" ) (progn (command "_.layer" "m" "TRONCO" "")(command "_.insert" "tronco_210.dwg" ponto escala "" "0" "")))
(( = Attv "220" ) (progn (command "_.layer" "m" "TRONCO" "")(command "_.insert" "tronco_220.dwg" ponto escala "" "0" "")))
(( = Attv "230" ) (progn (command "_.layer" "m" "TRONCO" "")(command "_.insert" "tronco_230.dwg" ponto escala "" "0" "")))
(( = Attv "240" ) (progn (command "_.layer" "m" "TRONCO" "")(command "_.insert" "tronco_240.dwg" ponto escala "" "0" "")))
				(( = Attv "250" ) (progn (command "_.layer" "m" "TRONCO" "")(command "_.insert" "tronco_250.dwg" ponto escala "" "0" "")))
(( = Attv "260" ) (progn (command "_.layer" "m" "TRONCO" "")(command "_.insert" "tronco_260.dwg" ponto escala "" "0" "")))
(( = Attv "270" ) (progn (command "_.layer" "m" "TRONCO" "")(command "_.insert" "tronco_270.dwg" ponto escala "" "0" "")))
(( = Attv "280" ) (progn (command "_.layer" "m" "TRONCO" "")(command "_.insert" "tronco_280.dwg" ponto escala "" "0" "")))
(( = Attv "290" ) (progn (command "_.layer" "m" "TRONCO" "")(command "_.insert" "tronco_290.dwg" ponto escala "" "0" "")))
				(( = Attv "300" ) (progn (command "_.layer" "m" "TRONCO" "")(command "_.insert" "tronco_300.dwg" ponto escala "" "0" "")))
(( = Attv "310" ) (progn (command "_.layer" "m" "TRONCO" "")(command "_.insert" "tronco_310.dwg" ponto escala "" "0" "")))
(( = Attv "320" ) (progn (command "_.layer" "m" "TRONCO" "")(command "_.insert" "tronco_320.dwg" ponto escala "" "0" "")))
(( = Attv "330" ) (progn (command "_.layer" "m" "TRONCO" "")(command "_.insert" "tronco_330.dwg" ponto escala "" "0" "")))
(( = Attv "340" ) (progn (command "_.layer" "m" "TRONCO" "")(command "_.insert" "tronco_340.dwg" ponto escala "" "0" "")))
				(( = Attv "350" ) (progn (command "_.layer" "m" "TRONCO" "")(command "_.insert" "tronco_350.dwg" ponto escala "" "0" "")))
(( = Attv "360" ) (progn (command "_.layer" "m" "TRONCO" "")(command "_.insert" "tronco_360.dwg" ponto escala "" "0" "")))
(( = Attv "370" ) (progn (command "_.layer" "m" "TRONCO" "")(command "_.insert" "tronco_370.dwg" ponto escala "" "0" "")))
(( = Attv "380" ) (progn (command "_.layer" "m" "TRONCO" "")(command "_.insert" "tronco_380.dwg" ponto escala "" "0" "")))
(( = Attv "390" ) (progn (command "_.layer" "m" "TRONCO" "")(command "_.insert" "tronco_390.dwg" ponto escala "" "0" "")))
				(( = Attv "400" ) (progn (command "_.layer" "m" "TRONCO" "")(command "_.insert" "tronco_400.dwg" ponto escala "" "0" "")))
(( = Attv "410" ) (progn (command "_.layer" "m" "TRONCO" "")(command "_.insert" "tronco_410.dwg" ponto escala "" "0" "")))
(( = Attv "420" ) (progn (command "_.layer" "m" "TRONCO" "")(command "_.insert" "tronco_420.dwg" ponto escala "" "0" "")))
(( = Attv "430" ) (progn (command "_.layer" "m" "TRONCO" "")(command "_.insert" "tronco_430.dwg" ponto escala "" "0" "")))
(( = Attv "440" ) (progn (command "_.layer" "m" "TRONCO" "")(command "_.insert" "tronco_440.dwg" ponto escala "" "0" "")))
				(( = Attv "450" ) (progn (command "_.layer" "m" "TRONCO" "")(command "_.insert" "tronco_150.dwg" ponto escala "" "0" "")))
(( = Attv "460" ) (progn (command "_.layer" "m" "TRONCO" "")(command "_.insert" "tronco_460.dwg" ponto escala "" "0" "")))
(( = Attv "470" ) (progn (command "_.layer" "m" "TRONCO" "")(command "_.insert" "tronco_470.dwg" ponto escala "" "0" "")))
(( = Attv "480" ) (progn (command "_.layer" "m" "TRONCO" "")(command "_.insert" "tronco_480.dwg" ponto escala "" "0" "")))
(( = Attv "490" ) (progn (command "_.layer" "m" "TRONCO" "")(command "_.insert" "tronco_490.dwg" ponto escala "" "0" "")))
				(( = Attv "500" ) (progn (command "_.layer" "m" "TRONCO" "")(command "_.insert" "tronco_500.dwg" ponto escala "" "0" "")))
(( = Attv "510" ) (progn (command "_.layer" "m" "TRONCO" "")(command "_.insert" "tronco_510.dwg" ponto escala "" "0" "")))
(( = Attv "520" ) (progn (command "_.layer" "m" "TRONCO" "")(command "_.insert" "tronco_520.dwg" ponto escala "" "0" "")))
(( = Attv "530" ) (progn (command "_.layer" "m" "TRONCO" "")(command "_.insert" "tronco_530.dwg" ponto escala "" "0" "")))
(( = Attv "540" ) (progn (command "_.layer" "m" "TRONCO" "")(command "_.insert" "tronco_540.dwg" ponto escala "" "0" "")))
				(( = Attv "550" ) (progn (command "_.layer" "m" "TRONCO" "")(command "_.insert" "tronco_550.dwg" ponto escala "" "0" "")))
(( = Attv "560" ) (progn (command "_.layer" "m" "TRONCO" "")(command "_.insert" "tronco_560.dwg" ponto escala "" "0" "")))
(( = Attv "570" ) (progn (command "_.layer" "m" "TRONCO" "")(command "_.insert" "tronco_570.dwg" ponto escala "" "0" "")))
(( = Attv "580" ) (progn (command "_.layer" "m" "TRONCO" "")(command "_.insert" "tronco_580.dwg" ponto escala "" "0" "")))
(( = Attv "590" ) (progn (command "_.layer" "m" "TRONCO" "")(command "_.insert" "tronco_590.dwg" ponto escala "" "0" "")))
				(( = Attv "600" ) (progn (command "_.layer" "m" "TRONCO" "")(command "_.insert" "tronco_600.dwg" ponto escala "" "0" "")))
(( = Attv "610" ) (progn (command "_.layer" "m" "TRONCO" "")(command "_.insert" "tronco_610.dwg" ponto escala "" "0" "")))
(( = Attv "620" ) (progn (command "_.layer" "m" "TRONCO" "")(command "_.insert" "tronco_620.dwg" ponto escala "" "0" "")))
(( = Attv "630" ) (progn (command "_.layer" "m" "TRONCO" "")(command "_.insert" "tronco_630.dwg" ponto escala "" "0" "")))
(( = Attv "640" ) (progn (command "_.layer" "m" "TRONCO" "")(command "_.insert" "tronco_640.dwg" ponto escala "" "0" "")))
				(( = Attv "650" ) (progn (command "_.layer" "m" "TRONCO" "")(command "_.insert" "tronco_650.dwg" ponto escala "" "0" "")))
(( = Attv "660" ) (progn (command "_.layer" "m" "TRONCO" "")(command "_.insert" "tronco_660.dwg" ponto escala "" "0" "")))
(( = Attv "670" ) (progn (command "_.layer" "m" "TRONCO" "")(command "_.insert" "tronco_670.dwg" ponto escala "" "0" "")))
(( = Attv "680" ) (progn (command "_.layer" "m" "TRONCO" "")(command "_.insert" "tronco_680.dwg" ponto escala "" "0" "")))
(( = Attv "690" ) (progn (command "_.layer" "m" "TRONCO" "")(command "_.insert" "tronco_690.dwg" ponto escala "" "0" "")))
				(( = Attv "700" ) (progn (command "_.layer" "m" "TRONCO" "")(command "_.insert" "tronco_700.dwg" ponto escala "" "0" "")))
(( = Attv "710" ) (progn (command "_.layer" "m" "TRONCO" "")(command "_.insert" "tronco_710.dwg" ponto escala "" "0" "")))
(( = Attv "720" ) (progn (command "_.layer" "m" "TRONCO" "")(command "_.insert" "tronco_720.dwg" ponto escala "" "0" "")))
(( = Attv "730" ) (progn (command "_.layer" "m" "TRONCO" "")(command "_.insert" "tronco_730.dwg" ponto escala "" "0" "")))
(( = Attv "740" ) (progn (command "_.layer" "m" "TRONCO" "")(command "_.insert" "tronco_740.dwg" ponto escala "" "0" "")))
				(( = Attv "750" ) (progn (command "_.layer" "m" "TRONCO" "")(command "_.insert" "tronco_750.dwg" ponto escala "" "0" "")))
(( = Attv "760" ) (progn (command "_.layer" "m" "TRONCO" "")(command "_.insert" "tronco_760.dwg" ponto escala "" "0" "")))
(( = Attv "770" ) (progn (command "_.layer" "m" "TRONCO" "")(command "_.insert" "tronco_770.dwg" ponto escala "" "0" "")))
(( = Attv "780" ) (progn (command "_.layer" "m" "TRONCO" "")(command "_.insert" "tronco_780.dwg" ponto escala "" "0" "")))
(( = Attv "790" ) (progn (command "_.layer" "m" "TRONCO" "")(command "_.insert" "tronco_790.dwg" ponto escala "" "0" "")))
				(( = Attv "800" ) (progn (command "_.layer" "m" "TRONCO" "")(command "_.insert" "tronco_800.dwg" ponto escala "" "0" "")))
(( = Attv "810" ) (progn (command "_.layer" "m" "TRONCO" "")(command "_.insert" "tronco_810.dwg" ponto escala "" "0" "")))
(( = Attv "820" ) (progn (command "_.layer" "m" "TRONCO" "")(command "_.insert" "tronco_820.dwg" ponto escala "" "0" "")))
(( = Attv "830" ) (progn (command "_.layer" "m" "TRONCO" "")(command "_.insert" "tronco_830.dwg" ponto escala "" "0" "")))
(( = Attv "840" ) (progn (command "_.layer" "m" "TRONCO" "")(command "_.insert" "tronco_840.dwg" ponto escala "" "0" "")))
				(( = Attv "850" ) (progn (command "_.layer" "m" "TRONCO" "")(command "_.insert" "tronco_850.dwg" ponto escala "" "0" "")))
(( = Attv "860" ) (progn (command "_.layer" "m" "TRONCO" "")(command "_.insert" "tronco_860.dwg" ponto escala "" "0" "")))
(( = Attv "870" ) (progn (command "_.layer" "m" "TRONCO" "")(command "_.insert" "tronco_870.dwg" ponto escala "" "0" "")))
(( = Attv "880" ) (progn (command "_.layer" "m" "TRONCO" "")(command "_.insert" "tronco_880.dwg" ponto escala "" "0" "")))
(( = Attv "890" ) (progn (command "_.layer" "m" "TRONCO" "")(command "_.insert" "tronco_890.dwg" ponto escala "" "0" "")))
				(( = Attv "900" ) (progn (command "_.layer" "m" "TRONCO" "")(command "_.insert" "tronco_900.dwg" ponto escala "" "0" "")))
(( = Attv "910" ) (progn (command "_.layer" "m" "TRONCO" "")(command "_.insert" "tronco_910.dwg" ponto escala "" "0" "")))
(( = Attv "920" ) (progn (command "_.layer" "m" "TRONCO" "")(command "_.insert" "tronco_920.dwg" ponto escala "" "0" "")))
(( = Attv "930" ) (progn (command "_.layer" "m" "TRONCO" "")(command "_.insert" "tronco_930.dwg" ponto escala "" "0" "")))
(( = Attv "940" ) (progn (command "_.layer" "m" "TRONCO" "")(command "_.insert" "tronco_940.dwg" ponto escala "" "0" "")))
				(( = Attv "950" ) (progn (command "_.layer" "m" "TRONCO" "")(command "_.insert" "tronco_950.dwg" ponto escala "" "0" "")))
(( = Attv "960" ) (progn (command "_.layer" "m" "TRONCO" "")(command "_.insert" "tronco_960.dwg" ponto escala "" "0" "")))
(( = Attv "970" ) (progn (command "_.layer" "m" "TRONCO" "")(command "_.insert" "tronco_970.dwg" ponto escala "" "0" "")))
(( = Attv "980" ) (progn (command "_.layer" "m" "TRONCO" "")(command "_.insert" "tronco_980.dwg" ponto escala "" "0" "")))
(( = Attv "990" ) (progn (command "_.layer" "m" "TRONCO" "")(command "_.insert" "tronco_990.dwg" ponto escala "" "0" "")))
				(( = Attv "1000" ) (progn (command "_.layer" "m" "TRONCO" "")(command "_.insert" "tronco_1000.dwg" ponto escala "" "0" "")))


                                    );;fim do cond
		    );;fim do progn
                          );;fim do if
	      );;fim do while
             );fim do while
      );fim do progn
) ;;fim do primeiro if
(setvar "cmdecho" olcmdecho)
(setvar "clayer" oldlayer)
(princ)
)
(princ "\nDigite 'TRONCO' para iniciar")
