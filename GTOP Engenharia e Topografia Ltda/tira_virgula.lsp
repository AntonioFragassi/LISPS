(defun tira_virgula (TEXTO / AUX j txt )
  	(setq comp (strlen TEXTO))
        (setq i 0)
        (setq aux "")
        (repeat (strlen TEXTO)
	  	(setq txt (substr TEXTO (setq i(1+ i)) 1))
	        (cond
		  ((= txt ",") (setq AUX (strcat aux "." )))
	          ((/= txt ".") (setq AUX (strcat aux txt )))
		 )
	)
  	(setq aux aux)
 )

(defun tira_ponto (TEXTO / AUX j txt )
  	(setq comp (strlen TEXTO))
        (setq i 0)
        (setq aux "")
        (repeat (strlen TEXTO)
	  	(setq txt (substr TEXTO (setq i(1+ i)) 1))
	        (cond
		  ((= txt ".") (setq AUX (strcat aux "" )))
	          ((/= txt ".") (setq AUX (strcat aux txt )))
		 )
	)
  	(setq aux aux)
 )


(defun RODA ( OBJETO / lista Attn Attv attn Novo_atomo1)
    (while (/= (cdr (assoc 0 (entget OBJETO))) "SEQEND")
        (setq lista (entget OBJETO))
        (setq Attn (cdr (assoc 2 lista)))
        (setq Attv (cdr (assoc 1 lista)))
        (if (= Attn "COTA")
	  (progn
	        (setq attv (tira_ponto Attv))
        	(setq attv (tira_virgula Attv))
        	(setq Novo_atomo1 (cons 1 attv))
        	(setq lista (subst Novo_atomo1 (assoc 1 lista) lista))
  		(entmod lista)
	   )
         )
        (setq OBJETO (entnext OBJETO))
     )	      
  ;(entupd lista)
)

(defun c:DECIMAL ( / )
    (setq Conjunto (ssget '((0 . "INSERT"))))
    (setq Comp_Conj (sslength Conjunto))
    (while (> Comp_Conj 0) ;; primeiro while
	  (progn
	      	(setq Comp_Conj (1- Comp_Conj))
	      	(setq OBJETO (ssname Conjunto Comp_Conj))
	        (RODA OBJETO)
	  );;fim do progn
     )
)
(princ "\nDigite 'DECIMAL' para iniciar")
