;; Coloca os blocos segundo a descrição 
(defun c:interlagos(/)
(princ "********* Espere um pouco - processando dados  ***********")
(setq olcmdecho (getvar "cmdecho"))
(setvar "cmdecho" 0)
(command "_.insert" "SIMB_PONTO_1.dwg" "201623.273676824,8243709.5027963" 1 "" "" "V-1")
(command "_.insert" "SIMB_PONTO_1.dwg" "201691.318411392,8243673.60057474" 1 "" "" "V-2")
(command "_.insert" "SIMB_PONTO_1.dwg" "201725.792945749,8243659.78305415" 1 "" "" "V-3")
(command "_.insert" "SIMB_PONTO_1.dwg" "201745.043364357,8243662.38534188" 1 "" "" "V-4")
(command "_.insert" "SIMB_PONTO_1.dwg" "201804.637836243,8243671.19778901" 1 "" "" "V-5")
(command "_.insert" "SIMB_PONTO_1.dwg" "201862.003034889,8243679.79815204" 1 "" "" "V-6")
(command "_.insert" "SIMB_PONTO_1.dwg" "201900.033988895,8243685.08925753" 1 "" "" "V-7")
(command "_.insert" "SIMB_PONTO_1.dwg" "201943.388751877,8243650.64617525" 1 "" "" "V-8")
(command "_.insert" "SIMB_PONTO_1.dwg" "201969.931501916,8243629.59138839" 1 "" "" "V-9")
(command "_.insert" "SIMB_PONTO_1.dwg" "201980.506536475,8243621.50523581" 1 "" "" "V-10")
(command "_.insert" "SIMB_PONTO_1.dwg" "201978.145510036,8243618.59863113" 1 "" "" "V-11")
(command "_.insert" "SIMB_PONTO_1.dwg" "201975.72828077,8243615.26294737" 1 "" "" "V-12")
(command "_.insert" "SIMB_PONTO_1.dwg" "201974.989912519,8243613.04200656" 1 "" "" "V-13")
(command "_.insert" "SIMB_PONTO_1.dwg" "201975.546858874,8243609.48855759" 1 "" "" "V-14")
(command "_.insert" "SIMB_PONTO_1.dwg" "201973.623043606,8243602.07519925" 1 "" "" "V-15")
(command "_.insert" "SIMB_PONTO_1.dwg" "201971.613706992,8243597.98255203" 1 "" "" "V-16")
(command "_.insert" "SIMB_PONTO_1.dwg" "201960.65654105,8243587.03270187" 1 "" "" "V-17")
(command "_.insert" "SIMB_PONTO_1.dwg" "201955.460091617,8243580.20572579" 1 "" "" "V-18")
(command "_.insert" "SIMB_PONTO_1.dwg" "201946.473731941,8243563.94855059" 1 "" "" "V-19")
(command "_.insert" "SIMB_PONTO_1.dwg" "201924.100590708,8243533.13476676" 1 "" "" "V-20")
(command "_.insert" "SIMB_PONTO_1.dwg" "201918.211570831,8243526.56182256" 1 "" "" "V-21")
(command "_.insert" "SIMB_PONTO_1.dwg" "201918.07563659,8243509.97014672" 1 "" "" "V-22")
(command "_.insert" "SIMB_PONTO_1.dwg" "201920.446442513,8243500.74745189" 1 "" "" "V-23")
(command "_.insert" "SIMB_PONTO_1.dwg" "201921.228014621,8243499.26707979" 1 "" "" "V-24")
(command "_.insert" "SIMB_PONTO_1.dwg" "201922.466171045,8243488.59005565" 1 "" "" "V-25")
(command "_.insert" "SIMB_PONTO_1.dwg" "201917.124515881,8243480.0186391" 1 "" "" "V-26")
(command "_.insert" "SIMB_PONTO_1.dwg" "201913.862976666,8243473.97628747" 1 "" "" "V-27")
(command "_.insert" "SIMB_PONTO_1.dwg" "201910.534945877,8243459.54975746" 1 "" "" "V-28")
(command "_.insert" "SIMB_PONTO_1.dwg" "201901.734396511,8243446.34967131" 1 "" "" "V-29")
(command "_.insert" "SIMB_PONTO_1.dwg" "201898.229635172,8243435.18942159" 1 "" "" "V-30")
(command "_.insert" "SIMB_PONTO_1.dwg" "201898.6223344,8243428.12521043" 1 "" "" "V-31")
(command "_.insert" "SIMB_PONTO_1.dwg" "201890.927304556,8243416.34941262" 1 "" "" "V-32")
(command "_.insert" "SIMB_PONTO_1.dwg" "201897.824405367,8243404.88426563" 1 "" "" "V-33")
(command "_.insert" "SIMB_PONTO_1.dwg" "201888.498050486,8243396.55679217" 1 "" "" "V-34")
(command "_.insert" "SIMB_PONTO_1.dwg" "201883.674482391,8243384.11697735" 1 "" "" "V-35")
(command "_.insert" "SIMB_PONTO_1.dwg" "201885.237049382,8243369.86482606" 1 "" "" "V-36")
(command "_.insert" "SIMB_PONTO_1.dwg" "201879.25107769,8243356.85096648" 1 "" "" "V-37")
(command "_.insert" "SIMB_PONTO_1.dwg" "201878.5019844,8243352.81310299" 1 "" "" "V-38")
(command "_.insert" "SIMB_PONTO_1.dwg" "201880.434375976,8243345.05092939" 1 "" "" "V-39")
(command "_.insert" "SIMB_PONTO_1.dwg" "201876.480274214,8243337.08407391" 1 "" "" "V-40")
(command "_.insert" "SIMB_PONTO_1.dwg" "201873.408218707,8243322.94331505" 1 "" "" "V-41")
(command "_.insert" "SIMB_PONTO_1.dwg" "201873.490757817,8243308.5885894" 1 "" "" "V-42")
(command "_.insert" "SIMB_PONTO_1.dwg" "201871.558446473,8243301.71533981" 1 "" "" "V-43")
(command "_.insert" "SIMB_PONTO_1.dwg" "201857.090150955,8243286.77278064" 1 "" "" "V-44")
(command "_.insert" "SIMB_PONTO_1.dwg" "201852.410200293,8243275.95283949" 1 "" "" "V-45")
(command "_.insert" "SIMB_PONTO_1.dwg" "201843.783637512,8243267.68934123" 1 "" "" "V-46")
(command "_.insert" "SIMB_PONTO_1.dwg" "201838.383341832,8243255.49571714" 1 "" "" "V-47")
(command "_.insert" "SIMB_PONTO_1.dwg" "201841.97328744,8243239.03075357" 1 "" "" "V-48")
(command "_.insert" "SIMB_PONTO_1.dwg" "201838.430700824,8243213.92749957" 1 "" "" "V-49")
(command "_.insert" "SIMB_PONTO_1.dwg" "201834.66373526,8243206.2755288" 1 "" "" "V-50")
(command "_.insert" "SIMB_PONTO_1.dwg" "201829.260928837,8243196.47505245" 1 "" "" "V-51")
(command "_.insert" "SIMB_PONTO_1.dwg" "201827.733143453,8243189.34769491" 1 "" "" "V-52")
(command "_.insert" "SIMB_PONTO_1.dwg" "201827.507749291,8243175.43353966" 1 "" "" "V-53")
(command "_.insert" "SIMB_PONTO_1.dwg" "201828.016066839,8243164.4653807" 1 "" "" "V-54")
(command "_.insert" "SIMB_PONTO_1.dwg" "201824.03,8243137.286" 1 "" "" "V-55")
(command "_.insert" "SIMB_PONTO_1.dwg" "201817.535,8243113.791" 1 "" "" "V-56")
(command "_.insert" "SIMB_PONTO_1.dwg" "201843.029,8243082.824" 1 "" "" "V-57")
(command "_.insert" "SIMB_PONTO_1.dwg" "201850.937,8243048.368" 1 "" "" "V-58")
(command "_.insert" "SIMB_PONTO_1.dwg" "201840.066,8243033.369" 1 "" "" "V-59")
(command "_.insert" "SIMB_PONTO_1.dwg" "201851.688,8243004.464" 1 "" "" "V-60")
(command "_.insert" "SIMB_PONTO_1.dwg" "201850.067,8242973.957" 1 "" "" "V-61")
(command "_.insert" "SIMB_PONTO_1.dwg" "201840.327,8242946.182" 1 "" "" "V-62")
(command "_.insert" "SIMB_PONTO_1.dwg" "201849.01,8242920.51599999" 1 "" "" "V-63")
(command "_.insert" "SIMB_PONTO_1.dwg" "201847.884,8242877.801" 1 "" "" "V-64")
(command "_.insert" "SIMB_PONTO_1.dwg" "201833.38,8242835.533" 1 "" "" "V-65")
(command "_.insert" "SIMB_PONTO_1.dwg" "201812.516,8242789.892" 1 "" "" "V-66")
(command "_.insert" "SIMB_PONTO_1.dwg" "201796.057,8242757.207" 1 "" "" "V-67")
(command "_.insert" "SIMB_PONTO_1.dwg" "201783.081,8242711.096" 1 "" "" "V-68")
(command "_.insert" "SIMB_PONTO_1.dwg" "201790.529,8242683.466" 1 "" "" "V-69")
(command "_.insert" "SIMB_PONTO_1.dwg" "201786.305,8242637.653" 1 "" "" "V-70")
(command "_.insert" "SIMB_PONTO_1.dwg" "201780.924,8242620.687" 1 "" "" "V-71")
(command "_.insert" "SIMB_PONTO_1.dwg" "201769.541,8242575.268" 1 "" "" "V-72")
(command "_.insert" "SIMB_PONTO_1.dwg" "201770.693,8242538.444" 1 "" "" "V-73")
(command "_.insert" "SIMB_PONTO_1.dwg" "201749.392335401,8242509.32937554" 1 "" "" "V-74")
(command "_.insert" "SIMB_PONTO_1.dwg" "201746.894989175,8242502.17223415" 1 "" "" "V-75")
(command "_.insert" "SIMB_PONTO_1.dwg" "201746.741296186,8242494.56546886" 1 "" "" "V-76")
(command "_.insert" "SIMB_PONTO_1.dwg" "201746.383730546,8242495.08347527" 1 "" "" "V-77")
(command "_.insert" "SIMB_PONTO_1.dwg" "201743.063477056,8242495.93211247" 1 "" "" "V-78")
(command "_.insert" "SIMB_PONTO_1.dwg" "201735.185575964,8242497.79510395" 1 "" "" "V-79")
(command "_.insert" "SIMB_PONTO_1.dwg" "201730.682209933,8242497.47137721" 1 "" "" "V-80")
(command "_.insert" "SIMB_PONTO_1.dwg" "201724.333896951,8242495.89298261" 1 "" "" "V-81")
(command "_.insert" "SIMB_PONTO_1.dwg" "201720.277487848,8242494.79394409" 1 "" "" "V-82")
(command "_.insert" "SIMB_PONTO_1.dwg" "201716.663520096,8242492.77816912" 1 "" "" "V-83")
(command "_.insert" "SIMB_PONTO_1.dwg" "201715.061804188,8242490.47980413" 1 "" "" "V-84")
(command "_.insert" "SIMB_PONTO_1.dwg" "201714.393013995,8242488.4793572" 1 "" "" "V-85")
(command "_.insert" "SIMB_PONTO_1.dwg" "201714.081276847,8242485.26646988" 1 "" "" "V-86")
(command "_.insert" "SIMB_PONTO_1.dwg" "201714.311586545,8242482.6331046" 1 "" "" "V-87")
(command "_.insert" "SIMB_PONTO_1.dwg" "201712.933171626,8242480.65078655" 1 "" "" "V-88")
(command "_.insert" "SIMB_PONTO_1.dwg" "201704.904238357,8242485.13078129" 1 "" "" "V-89")
(command "_.insert" "SIMB_PONTO_1.dwg" "201697.994576591,8242485.84164319" 1 "" "" "V-90")
(command "_.insert" "SIMB_PONTO_1.dwg" "201697.100341978,8242487.56981483" 1 "" "" "V-91")
(command "_.insert" "SIMB_PONTO_1.dwg" "201694.135330729,8242489.97054971" 1 "" "" "V-92")
(command "_.insert" "SIMB_PONTO_1.dwg" "201690.941499617,8242491.16755241" 1 "" "" "V-93")
(command "_.insert" "SIMB_PONTO_1.dwg" "201691.233297992,8242495.14073459" 1 "" "" "V-94")
(command "_.insert" "SIMB_PONTO_1.dwg" "201691.591566965,8242497.89721591" 1 "" "" "V-95")
(command "_.insert" "SIMB_PONTO_1.dwg" "201688.198530384,8242506.01249506" 1 "" "" "V-96")
(command "_.insert" "SIMB_PONTO_1.dwg" "201686.248398953,8242508.79974275" 1 "" "" "V-97")
(command "_.insert" "SIMB_PONTO_1.dwg" "201682.625615427,8242513.44687584" 1 "" "" "V-98")
(command "_.insert" "SIMB_PONTO_1.dwg" "201679.853185651,8242512.68794838" 1 "" "" "V-99")
(command "_.insert" "SIMB_PONTO_1.dwg" "201676.468113608,8242514.07519406" 1 "" "" "V-100")
(command "_.insert" "SIMB_PONTO_1.dwg" "201673.000192002,8242516.71919671" 1 "" "" "V-101")
(command "_.insert" "SIMB_PONTO_1.dwg" "201668.722240451,8242521.5636796" 1 "" "" "V-102")
(command "_.insert" "SIMB_PONTO_1.dwg" "201663.310137971,8242533.29265169" 1 "" "" "V-103")
(command "_.insert" "SIMB_PONTO_1.dwg" "201661.145029189,8242533.54219664" 1 "" "" "V-104")
(command "_.insert" "SIMB_PONTO_1.dwg" "201653.965134881,8242536.64658809" 1 "" "" "V-105")
(command "_.insert" "SIMB_PONTO_1.dwg" "201652.120297713,8242537.2098139" 1 "" "" "V-106")
(command "_.insert" "SIMB_PONTO_1.dwg" "201644.082047359,8242540.36041307" 1 "" "" "V-107")
(command "_.insert" "SIMB_PONTO_1.dwg" "201639.013794723,8242542.39752078" 1 "" "" "V-108")
(command "_.insert" "SIMB_PONTO_1.dwg" "201639.623591778,8242544.19086891" 1 "" "" "V-109")
(command "_.insert" "SIMB_PONTO_1.dwg" "201639.580432068,8242545.50770341" 1 "" "" "V-110")
(command "_.insert" "SIMB_PONTO_1.dwg" "201643.174450124,8242551.85940267" 1 "" "" "V-111")
(command "_.insert" "SIMB_PONTO_1.dwg" "201643.277689646,8242555.00340176" 1 "" "" "V-112")
(command "_.insert" "SIMB_PONTO_1.dwg" "201639.138336205,8242557.90125818" 1 "" "" "V-113")
(command "_.insert" "SIMB_PONTO_1.dwg" "201634.98114206,8242557.28699495" 1 "" "" "V-114")
(command "_.insert" "SIMB_PONTO_1.dwg" "201628.34581073,8242557.22168668" 1 "" "" "V-115")
(command "_.insert" "SIMB_PONTO_1.dwg" "201626.227825384,8242557.80029022" 1 "" "" "V-116")
(command "_.insert" "SIMB_PONTO_1.dwg" "201623.171152806,8242561.86063116" 1 "" "" "V-117")
(command "_.insert" "SIMB_PONTO_1.dwg" "201620.656778801,8242565.67402978" 1 "" "" "V-118")
(command "_.insert" "SIMB_PONTO_1.dwg" "201616.206387368,8242573.53363242" 1 "" "" "V-119")
(command "_.insert" "SIMB_PONTO_1.dwg" "201622.595516184,8242575.7559692" 1 "" "" "V-120")
(command "_.insert" "SIMB_PONTO_1.dwg" "201624.141686802,8242576.19373621" 1 "" "" "V-121")
(command "_.insert" "SIMB_PONTO_1.dwg" "201627.130807973,8242578.34638961" 1 "" "" "V-122")
(command "_.insert" "SIMB_PONTO_1.dwg" "201630.056306551,8242581.76458046" 1 "" "" "V-123")
(command "_.insert" "SIMB_PONTO_1.dwg" "201629.01762476,8242584.91580816" 1 "" "" "V-124")
(command "_.insert" "SIMB_PONTO_1.dwg" "201628.344706101,8242587.31692152" 1 "" "" "V-125")
(command "_.insert" "SIMB_PONTO_1.dwg" "201627.404993823,8242592.29454059" 1 "" "" "V-126")
(command "_.insert" "SIMB_PONTO_1.dwg" "201627.683502116,8242592.84558331" 1 "" "" "V-127")
(command "_.insert" "SIMB_PONTO_1.dwg" "201627.910519101,8242594.07078133" 1 "" "" "V-128")
(command "_.insert" "SIMB_PONTO_1.dwg" "201629.300197962,8242597.054883" 1 "" "" "V-129")
(command "_.insert" "SIMB_PONTO_1.dwg" "201630.506324761,8242599.12272677" 1 "" "" "V-130")
(command "_.insert" "SIMB_PONTO_1.dwg" "201628.577218563,8242603.3543506" 1 "" "" "V-131")
(command "_.insert" "SIMB_PONTO_1.dwg" "201624.90582478,8242603.22194588" 1 "" "" "V-132")
(command "_.insert" "SIMB_PONTO_1.dwg" "201621.599107009,8242603.4629874" 1 "" "" "V-133")
(command "_.insert" "SIMB_PONTO_1.dwg" "201617.635387982,8242609.83584979" 1 "" "" "V-134")
(command "_.insert" "SIMB_PONTO_1.dwg" "201615.691475068,8242612.98184852" 1 "" "" "V-135")
(command "_.insert" "SIMB_PONTO_1.dwg" "201614.887823221,8242617.59596785" 1 "" "" "V-136")
(command "_.insert" "SIMB_PONTO_1.dwg" "201613.739688392,8242622.578514" 1 "" "" "V-137")
(command "_.insert" "SIMB_PONTO_1.dwg" "201612.916873807,8242625.16729723" 1 "" "" "V-138")
(command "_.insert" "SIMB_PONTO_1.dwg" "201612.067679489,8242626.65143415" 1 "" "" "V-139")
(command "_.insert" "SIMB_PONTO_1.dwg" "201611.117297463,8242628.77163425" 1 "" "" "V-140")
(command "_.insert" "SIMB_PONTO_1.dwg" "201605.695477753,8242630.52066367" 1 "" "" "V-141")
(command "_.insert" "SIMB_PONTO_1.dwg" "201604.86046331,8242630.00442319" 1 "" "" "V-142")
(command "_.insert" "SIMB_PONTO_1.dwg" "201600.465175342,8242631.60473816" 1 "" "" "V-143")
(command "_.insert" "SIMB_PONTO_1.dwg" "201599.641103178,8242632.76642594" 1 "" "" "V-144")
(command "_.insert" "SIMB_PONTO_1.dwg" "201598.627850105,8242634.7090855" 1 "" "" "V-145")
(command "_.insert" "SIMB_PONTO_1.dwg" "201599.018751198,8242636.54784894" 1 "" "" "V-146")
(command "_.insert" "SIMB_PONTO_1.dwg" "201598.234767583,8242638.67075977" 1 "" "" "V-147")
(command "_.insert" "SIMB_PONTO_1.dwg" "201593.745714262,8242640.31857146" 1 "" "" "V-148")
(command "_.insert" "SIMB_PONTO_1.dwg" "201591.871440791,8242640.34508009" 1 "" "" "V-149")
(command "_.insert" "SIMB_PONTO_1.dwg" "201590.06093189,8242640.16743491" 1 "" "" "V-150")
(command "_.insert" "SIMB_PONTO_1.dwg" "201585.946382974,8242634.29208863" 1 "" "" "V-151")
(command "_.insert" "SIMB_PONTO_1.dwg" "201585.643761607,8242633.91302233" 1 "" "" "V-152")
(command "_.insert" "SIMB_PONTO_1.dwg" "201582.45729452,8242634.68184515" 1 "" "" "V-153")
(command "_.insert" "SIMB_PONTO_1.dwg" "201582.049492382,8242635.47435174" 1 "" "" "V-154")
(command "_.insert" "SIMB_PONTO_1.dwg" "201581.483391031,8242638.26638125" 1 "" "" "V-155")
(command "_.insert" "SIMB_PONTO_1.dwg" "201580.472347275,8242640.81350863" 1 "" "" "V-156")
(command "_.insert" "SIMB_PONTO_1.dwg" "201576.46070624,8242642.07463283" 1 "" "" "V-157")
(command "_.insert" "SIMB_PONTO_1.dwg" "201573.838882108,8242642.82052525" 1 "" "" "V-158")
(command "_.insert" "SIMB_PONTO_1.dwg" "201573.827498177,8242643.17827704" 1 "" "" "V-159")
(command "_.insert" "SIMB_PONTO_1.dwg" "201574.863735873,8242643.6219612" 1 "" "" "V-160")
(command "_.insert" "SIMB_PONTO_1.dwg" "201576.696671753,8242644.86085214" 1 "" "" "V-161")
(command "_.insert" "SIMB_PONTO_1.dwg" "201577.582475831,8242646.75246027" 1 "" "" "V-162")
(command "_.insert" "SIMB_PONTO_1.dwg" "201577.683966434,8242649.36730111" 1 "" "" "V-163")
(command "_.insert" "SIMB_PONTO_1.dwg" "201577.278255193,8242652.76833321" 1 "" "" "V-164")
(command "_.insert" "SIMB_PONTO_1.dwg" "201574.522298072,8242655.71651277" 1 "" "" "V-165")
(command "_.insert" "SIMB_PONTO_1.dwg" "201571.409270231,8242657.57402174" 1 "" "" "V-166")
(command "_.insert" "SIMB_PONTO_1.dwg" "201569.980995461,8242659.01413617" 1 "" "" "V-167")
(command "_.insert" "SIMB_PONTO_1.dwg" "201569.684621557,8242660.25654861" 1 "" "" "V-168")
(command "_.insert" "SIMB_PONTO_1.dwg" "201569.097952377,8242661.39838655" 1 "" "" "V-169")
(command "_.insert" "SIMB_PONTO_1.dwg" "201568.571685809,8242662.8323757" 1 "" "" "V-170")
(command "_.insert" "SIMB_PONTO_1.dwg" "201569.158833127,8242664.90160145" 1 "" "" "V-171")
(command "_.insert" "SIMB_PONTO_1.dwg" "201568.083807511,8242667.07618464" 1 "" "" "V-172")
(command "_.insert" "SIMB_PONTO_1.dwg" "201567.308947271,8242668.03999588" 1 "" "" "V-173")
(command "_.insert" "SIMB_PONTO_1.dwg" "201565.247557885,8242669.02039548" 1 "" "" "V-174")
(command "_.insert" "SIMB_PONTO_1.dwg" "201561.891454284,8242673.45739637" 1 "" "" "V-175")
(command "_.insert" "SIMB_PONTO_1.dwg" "201559.345422226,8242677.807383" 1 "" "" "V-176")
(command "_.insert" "SIMB_PONTO_1.dwg" "201558.081670309,8242679.39990254" 1 "" "" "V-177")
(command "_.insert" "SIMB_PONTO_1.dwg" "201557.875148922,8242683.97143294" 1 "" "" "V-178")
(command "_.insert" "SIMB_PONTO_1.dwg" "201554.016721785,8242687.39960692" 1 "" "" "V-179")
(command "_.insert" "SIMB_PONTO_1.dwg" "201549.330012297,8242691.81947849" 1 "" "" "V-180")
(command "_.insert" "SIMB_PONTO_1.dwg" "201547.055954837,8242694.90844682" 1 "" "" "V-181")
(command "_.insert" "SIMB_PONTO_1.dwg" "201547.014055513,8242696.4542439" 1 "" "" "V-182")
(command "_.insert" "SIMB_PONTO_1.dwg" "201542.265489474,8242698.90294518" 1 "" "" "V-183")
(command "_.insert" "SIMB_PONTO_1.dwg" "201539.714092927,8242703.28990187" 1 "" "" "V-184")
(command "_.insert" "SIMB_PONTO_1.dwg" "201537.832121221,8242703.91186755" 1 "" "" "V-185")
(command "_.insert" "SIMB_PONTO_1.dwg" "201535.673935274,8242702.93690542" 1 "" "" "V-186")
(command "_.insert" "SIMB_PONTO_1.dwg" "201531.82818863,8242701.60234238" 1 "" "" "V-187")
(command "_.insert" "SIMB_PONTO_1.dwg" "201525.286278006,8242701.32647544" 1 "" "" "V-188")
(command "_.insert" "SIMB_PONTO_1.dwg" "201522.103275909,8242701.87438042" 1 "" "" "V-189")
(command "_.insert" "SIMB_PONTO_1.dwg" "201515.210482492,8242703.12360211" 1 "" "" "V-190")
(command "_.insert" "SIMB_PONTO_1.dwg" "201511.78680492,8242703.33922972" 1 "" "" "V-191")
(command "_.insert" "SIMB_PONTO_1.dwg" "201506.982427823,8242703.35653973" 1 "" "" "V-192")
(command "_.insert" "SIMB_PONTO_1.dwg" "201505.020579751,8242701.96150436" 1 "" "" "V-193")
(command "_.insert" "SIMB_PONTO_1.dwg" "201503.353264388,8242702.10443729" 1 "" "" "V-194")
(command "_.insert" "SIMB_PONTO_1.dwg" "201495.809062307,8242704.33286245" 1 "" "" "V-195")
(command "_.insert" "SIMB_PONTO_1.dwg" "201493.95333408,8242705.85727993" 1 "" "" "V-196")
(command "_.insert" "SIMB_PONTO_1.dwg" "201492.725850292,8242707.22732405" 1 "" "" "V-197")
(command "_.insert" "SIMB_PONTO_1.dwg" "201492.622705315,8242707.52868966" 1 "" "" "V-198")
(command "_.insert" "SIMB_PONTO_1.dwg" "201493.483959907,8242709.21502181" 1 "" "" "V-199")
(command "_.insert" "SIMB_PONTO_1.dwg" "201494.812521703,8242710.73422789" 1 "" "" "V-200")
(command "_.insert" "SIMB_PONTO_1.dwg" "201495.407844741,8242711.97939285" 1 "" "" "V-201")
(command "_.insert" "SIMB_PONTO_1.dwg" "201495.110233254,8242714.03443253" 1 "" "" "V-202")
(command "_.insert" "SIMB_PONTO_1.dwg" "201492.234820185,8242715.40927159" 1 "" "" "V-203")
(command "_.insert" "SIMB_PONTO_1.dwg" "201487.983688651,8242717.74574066" 1 "" "" "V-204")
(command "_.insert" "SIMB_PONTO_1.dwg" "201486.512774916,8242718.99886185" 1 "" "" "V-205")
(command "_.insert" "SIMB_PONTO_1.dwg" "201485.811120303,8242724.69596149" 1 "" "" "V-206")
(command "_.insert" "SIMB_PONTO_1.dwg" "201484.639619047,8242726.74159512" 1 "" "" "V-207")
(command "_.insert" "SIMB_PONTO_1.dwg" "201482.10324717,8242728.20885477" 1 "" "" "V-208")
(command "_.insert" "SIMB_PONTO_1.dwg" "201480.422237566,8242728.36769552" 1 "" "" "V-209")
(command "_.insert" "SIMB_PONTO_1.dwg" "201478.792137858,8242732.3103741" 1 "" "" "V-210")
(command "_.insert" "SIMB_PONTO_1.dwg" "201478.995005785,8242735.20672166" 1 "" "" "V-211")
(command "_.insert" "SIMB_PONTO_1.dwg" "201479.470134746,8242736.56744472" 1 "" "" "V-212")
(command "_.insert" "SIMB_PONTO_1.dwg" "201481.50807473,8242738.37906135" 1 "" "" "V-213")
(command "_.insert" "SIMB_PONTO_1.dwg" "201482.970423397,8242740.72146336" 1 "" "" "V-214")
(command "_.insert" "SIMB_PONTO_1.dwg" "201482.352176696,8242741.35859721" 1 "" "" "V-215")
(command "_.insert" "SIMB_PONTO_1.dwg" "201481.953419792,8242743.03704667" 1 "" "" "V-216")
(command "_.insert" "SIMB_PONTO_1.dwg" "201477.761722764,8242742.95712188" 1 "" "" "V-217")
(command "_.insert" "SIMB_PONTO_1.dwg" "201473.684555817,8242743.37484235" 1 "" "" "V-218")
(command "_.insert" "SIMB_PONTO_1.dwg" "201471.655072729,8242743.33409061" 1 "" "" "V-219")
(command "_.insert" "SIMB_PONTO_1.dwg" "201467.681819506,8242743.07740965" 1 "" "" "V-220")
(command "_.insert" "SIMB_PONTO_1.dwg" "201462.828740857,8242742.81244604" 1 "" "" "V-221")
(command "_.insert" "SIMB_PONTO_1.dwg" "201460.245228257,8242742.26015302" 1 "" "" "V-222")
(command "_.insert" "SIMB_PONTO_1.dwg" "201458.332854734,8242741.24503159" 1 "" "" "V-223")
(command "_.insert" "SIMB_PONTO_1.dwg" "201457.043307945,8242737.62011511" 1 "" "" "V-224")
(command "_.insert" "SIMB_PONTO_1.dwg" "201455.307092473,8242734.68866278" 1 "" "" "V-225")
(command "_.insert" "SIMB_PONTO_1.dwg" "201452.38340837,8242734.17358703" 1 "" "" "V-226")
(command "_.insert" "SIMB_PONTO_1.dwg" "201448.2667863,8242734.26625348" 1 "" "" "V-227")
(command "_.insert" "SIMB_PONTO_1.dwg" "201440.511065515,8242736.12418058" 1 "" "" "V-228")
(command "_.insert" "SIMB_PONTO_1.dwg" "201441.921182793,8242738.79559172" 1 "" "" "V-229")
(command "_.insert" "SIMB_PONTO_1.dwg" "201444.550224281,8242740.97261079" 1 "" "" "V-230")
(command "_.insert" "SIMB_PONTO_1.dwg" "201447.201878782,8242743.47438328" 1 "" "" "V-231")
(command "_.insert" "SIMB_PONTO_1.dwg" "201448.038129174,8242746.82159043" 1 "" "" "V-232")
(command "_.insert" "SIMB_PONTO_1.dwg" "201449.249529886,8242750.34158147" 1 "" "" "V-233")
(command "_.insert" "SIMB_PONTO_1.dwg" "201452.127045735,8242753.26778355" 1 "" "" "V-234")
(command "_.insert" "SIMB_PONTO_1.dwg" "201448.248595697,8242755.90727735" 1 "" "" "V-235")
(command "_.insert" "SIMB_PONTO_1.dwg" "201445.923098058,8242757.05255027" 1 "" "" "V-236")
(command "_.insert" "SIMB_PONTO_1.dwg" "201443.786990963,8242758.17346451" 1 "" "" "V-237")
(command "_.insert" "SIMB_PONTO_1.dwg" "201441.255121092,8242758.96524735" 1 "" "" "V-238")
(command "_.insert" "SIMB_PONTO_1.dwg" "201439.146538747,8242758.27795905" 1 "" "" "V-239")
(command "_.insert" "SIMB_PONTO_1.dwg" "201436.49086797,8242758.02003267" 1 "" "" "V-240")
(command "_.insert" "SIMB_PONTO_1.dwg" "201434.946906814,8242756.2758625" 1 "" "" "V-241")
(command "_.insert" "SIMB_PONTO_1.dwg" "201434.283554864,8242755.3290715" 1 "" "" "V-242")
(command "_.insert" "SIMB_PONTO_1.dwg" "201431.667588938,8242755.83007825" 1 "" "" "V-243")
(command "_.insert" "SIMB_PONTO_1.dwg" "201429.848895449,8242756.8234983" 1 "" "" "V-244")
(command "_.insert" "SIMB_PONTO_1.dwg" "201427.061581557,8242758.35578933" 1 "" "" "V-245")
(command "_.insert" "SIMB_PONTO_1.dwg" "201425.546609242,8242757.93185837" 1 "" "" "V-246")
(command "_.insert" "SIMB_PONTO_1.dwg" "201424.02622746,8242757.34083702" 1 "" "" "V-247")
(command "_.insert" "SIMB_PONTO_1.dwg" "201419.27229633,8242759.2579063" 1 "" "" "V-248")
(command "_.insert" "SIMB_PONTO_1.dwg" "201416.859414213,8242760.45873035" 1 "" "" "V-249")
(command "_.insert" "SIMB_PONTO_1.dwg" "201415.921655824,8242763.17900769" 1 "" "" "V-250")
(command "_.insert" "SIMB_PONTO_1.dwg" "201413.523311495,8242767.07416667" 1 "" "" "V-251")
(command "_.insert" "SIMB_PONTO_1.dwg" "201407.712038478,8242766.45449281" 1 "" "" "V-252")
(command "_.insert" "SIMB_PONTO_1.dwg" "201404.329301895,8242768.17715235" 1 "" "" "V-253")
(command "_.insert" "SIMB_PONTO_1.dwg" "201403.56727963,8242771.43458112" 1 "" "" "V-254")
(command "_.insert" "SIMB_PONTO_1.dwg" "201402.95184367,8242778.66452576" 1 "" "" "V-255")
(command "_.insert" "SIMB_PONTO_1.dwg" "201401.592663885,8242779.30074474" 1 "" "" "V-256")
(command "_.insert" "SIMB_PONTO_1.dwg" "201400.049599678,8242780.24384505" 1 "" "" "V-257")
(command "_.insert" "SIMB_PONTO_1.dwg" "201396.539227553,8242778.31771528" 1 "" "" "V-258")
(command "_.insert" "SIMB_PONTO_1.dwg" "201395.476783844,8242776.88066973" 1 "" "" "V-259")
(command "_.insert" "SIMB_PONTO_1.dwg" "201391.958126288,8242775.36275785" 1 "" "" "V-260")
(command "_.insert" "SIMB_PONTO_1.dwg" "201386.755954354,8242773.03996973" 1 "" "" "V-261")
(command "_.insert" "SIMB_PONTO_1.dwg" "201384.298943101,8242775.30016363" 1 "" "" "V-262")
(command "_.insert" "SIMB_PONTO_1.dwg" "201381.999187813,8242777.90730907" 1 "" "" "V-263")
(command "_.insert" "SIMB_PONTO_1.dwg" "201378.06611889,8242781.86524541" 1 "" "" "V-264")
(command "_.insert" "SIMB_PONTO_1.dwg" "201372.846710609,8242787.97486563" 1 "" "" "V-265")
(command "_.insert" "SIMB_PONTO_1.dwg" "201372.503561353,8242792.07533183" 1 "" "" "V-266")
(command "_.insert" "SIMB_PONTO_1.dwg" "201372.391897926,8242795.44993902" 1 "" "" "V-267")
(command "_.insert" "SIMB_PONTO_1.dwg" "201370.959175868,8242799.23361772" 1 "" "" "V-268")
(command "_.insert" "SIMB_PONTO_1.dwg" "201369.804101905,8242801.96228506" 1 "" "" "V-269")
(command "_.insert" "SIMB_PONTO_1.dwg" "201368.838834831,8242803.00884967" 1 "" "" "V-270")
(command "_.insert" "SIMB_PONTO_1.dwg" "201367.911310832,8242803.47403705" 1 "" "" "V-271")
(command "_.insert" "SIMB_PONTO_1.dwg" "201367.42846737,8242803.43006333" 1 "" "" "V-272")
(command "_.insert" "SIMB_PONTO_1.dwg" "201400.887223456,8242922.31055809" 1 "" "" "V-273")
(command "_.insert" "SIMB_PONTO_1.dwg" "201434.673211102,8243042.45050476" 1 "" "" "V-274")
(command "_.insert" "SIMB_PONTO_1.dwg" "201479.857534609,8243201.92946451" 1 "" "" "V-275")
(command "_.insert" "SIMB_PONTO_1.dwg" "201515.14809557,8243327.34847251" 1 "" "" "V-276")
(command "_.insert" "SIMB_PONTO_1.dwg" "201560.304682675,8243486.63057642" 1 "" "" "V-277")
(command "_.insert" "SIMB_PONTO_1.dwg" "201605.104550283,8243645.36492583" 1 "" "" "V-278")
(setvar "cmdecho" olcmdecho)
(setvar "clayer" oldlayer)
(princ)
)
(princ "\nDigite 'interlagos' para iniciar")
