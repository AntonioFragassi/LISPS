(defun C:COTA ( / )
        (setq Ptins (c:cal "0+0"))
        (command "_.-Layer" "m" "TEXTO" "")
        (command "_.-Layer" "m" "LINHA_CHAMADA" "")
        (setq Ht 0.16)
        (setq ponto_base (car (cdr (getpoint "\nClique no ponto base: " ))))
        (setq cota (getreal "\nForneça a cota base: "))
        (setq fator (/ cota ponto_base))
        (while (setq ponto_base (getpoint "\nClique no ponto: " ))
             (setq cota_base (car (cdr ponto_base )))
        	(setq Cota (* cota_base fator ))
             (setq P1  (getpoint "\nOnde que escrever?: " ) )
              (command "_.-Layer" "m" "LINHA_CHAMADA" "")
        	(command "_.line" ponto_base  P1 "")
             (setq P2 (c:cal "P2 + [0,0.08,0]"))
             (command "_.-Layer" "m" "TEXTO")
        	(command "_.text" P2 Ht "0.0" (rtos Cota 2 3) )
             (command "_.-Layer" "m" "LINHA_CHAMADA" "")
        	(command "_.line" P1 (getpoint) "")
       );;fim do while
)
(princ "\n")
(prompt "Digite 'COTA' para exportação de vértices a longo da polyline")
