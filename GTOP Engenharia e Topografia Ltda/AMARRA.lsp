(defun c:AMARRA ( / P1 P2 ANG DIST)
  (command "_.layer" "m" "TXT_PECAS_ESGOTO" "")
  (while T
        (setvar "osmode" 1)
      	(command "line" (setq P1 (getpoint "Ponto 1:")) (setq P2 (getpoint "Ponto 2:")) "")
        (command "_.change" "L" "" "P" "c" 1 "")
      	(setq ANG (atof (angtos (angle P1 P2)0 12)))
        (setq DIST (DISTANCe P1 P2))
        (setvar "osmode" 0)
        (command "insert" "T:\\Biblioteca CAD\\Blocos\\CAESB\\TRACO.dwg" P1 "" "" ANG "")
        (command "insert" "T:\\Biblioteca CAD\\Blocos\\CAESB\\TRACO.dwg" P2 "" "" ANG "")
        (cond
		((and (>= ANG 0.0)(< ANG 90.0))
		   (command "insert" "T:\\Biblioteca CAD\\Blocos\\CAESB\\COTA_D.dwg" P2 "" "" ANG (rtos DIST 2 2) "")
		 )
		((and (>= ANG 270.0)(< ANG 360.0))
		   (command "insert" "T:\\Biblioteca CAD\\Blocos\\CAESB\\COTA_D.dwg" P2 "" "" ANG (rtos DIST 2 2) "")
		 )
		((and (>= ANG 90.0)(< ANG 270.0))
		   (command "insert" "T:\\Biblioteca CAD\\Blocos\\CAESB\\COTA_E.dwg" P2 "" "" (- ANG 180.0) (rtos DIST 2 2) "")
		 )
	  )
    )
  )

(princ "\nDigite 'AMARRA' para iniciar")
