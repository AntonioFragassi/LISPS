;; Coloca os blocos segundo a descrição 
(defun c:belvedere(/)
(princ "********* Espere um pouco - processando dados  ***********")
(setq olcmdecho (getvar "cmdecho"))
(setvar "cmdecho" 0)
(command "_.layer" "m" "VERTICES_TIPO_M" "")
(command "_.insert" "INCRA_vertice_M" "205466.904246815,8244256.0288355" "0.1" "" "0" "A0D-M-1659" "")
(command "_.insert" "INCRA_vertice_M" "205588.54378524,8244273.00255493" "0.1" "" "0" "A0D-M-1660" "")
(command "_.insert" "INCRA_vertice_M" "205630.647636283,8244279.72814607" "0.1" "" "0" "A0D-M-1662" "")
(command "_.insert" "INCRA_vertice_M" "205714.672401486,8244292.22866448" "0.1" "" "0" "A0D-M-1663" "")
(command "_.insert" "INCRA_vertice_M" "205810.85932142,8244306.55606674" "0.1" "" "0" "A0D-M-1664" "")
(command "_.insert" "INCRA_vertice_M" "205817.432946145,8244307.36993392" "0.1" "" "0" "A0D-M-1665" "")
(command "_.insert" "INCRA_vertice_M" "205825.369617411,8244303.21591878" "0.1" "" "0" "A0D-M-1666" "")
(command "_.insert" "INCRA_vertice_M" "205829.912999999,8244294.053" "0.1" "" "0" "A0D-M-1667" "")
(command "_.insert" "INCRA_vertice_M" "205842.163935724,8244270.02009313" "0.1" "" "0" "A0D-M-1668" "")
(command "_.insert" "INCRA_vertice_M" "205875.333,8244210.101" "0.1" "" "0" "A0D-M-1669" "")
(command "_.insert" "INCRA_vertice_M" "206087.757935724,8244321.88509313" "0.1" "" "0" "A0D-M-1670" "")
(command "_.insert" "INCRA_vertice_M" "206094.375935724,8244378.35309312" "0.1" "" "0" "A0D-M-1671" "")
(command "_.insert" "INCRA_vertice_M" "206113.816649137,8244325.73596548" "0.1" "" "0" "A0D-M-1672" "")
(command "_.insert" "INCRA_vertice_M" "205879.967145985,8244202.39374276" "0.1" "" "0" "A0D-M-1673" "")
(command "_.insert" "INCRA_vertice_M" "205882.540949062,8244197.99082088" "0.1" "" "0" "A0D-M-1674" "")
(command "_.insert" "INCRA_vertice_M" "205881.432794744,8244196.16318018" "0.1" "" "0" "A0D-M-1675" "")
(command "_.insert" "INCRA_vertice_M" "205928.041618065,8244135.03873909" "0.1" "" "0" "A0D-M-1676" "")
(command "_.insert" "INCRA_vertice_M" "205955.782956182,8244101.99624256" "0.1" "" "0" "A0D-M-1677" "")
(command "_.insert" "INCRA_vertice_M" "205976.524552544,8244067.78485321" "0.1" "" "0" "A0D-M-1678" "")
(command "_.insert" "INCRA_vertice_M" "206077.018508487,8244125.78608082" "0.1" "" "0" "A0D-M-1679" "")
(command "_.insert" "INCRA_vertice_M" "206124.51172117,8244156.91901354" "0.1" "" "0" "A0D-M-1680" "")
(command "_.insert" "INCRA_vertice_M" "206141.109311333,8243881.67383579" "0.1" "" "0" "A0D-M-1681" "")
(command "_.insert" "INCRA_vertice_M" "206082.525614668,8243882.90513537" "0.1" "" "0" "A0D-M-1682" "")
(command "_.insert" "INCRA_vertice_M" "206102.76274425,8243851.61738852" "0.1" "" "0" "A0D-M-1683" "")
(command "_.insert" "INCRA_vertice_M" "206080.655995227,8243836.93946727" "0.1" "" "0" "A0D-M-1684" "")
(command "_.insert" "INCRA_vertice_M" "206099.074912011,8243831.1569059" "0.1" "" "0" "A0D-M-1685" "")
(command "_.insert" "INCRA_vertice_M" "206214.615500372,8243796.76416826" "0.1" "" "0" "A0D-M-1686" "")
(command "_.insert" "INCRA_vertice_M" "205521.384736707,8243557.295397" "0.1" "" "0" "CWM-M-1401" "")
(command "_.insert" "INCRA_vertice_M" "204381.452681349,8243512.26558423" "0.1" "" "0" "A0D-M-1031" "")
(command "_.insert" "INCRA_vertice_M" "204355.218,8243508.214" "0.1" "" "0" "A0D-M-1687" "")
(command "_.insert" "INCRA_vertice_M" "204878.212184427,8244062.36291151" "0.1" "" "0" "A0D-M-1692" "")
(command "_.insert" "INCRA_vertice_M" "204909.666758162,8244050.19602128" "0.1" "" "0" "A0D-M-1693" "")
(command "_.insert" "INCRA_vertice_M" "204934.88378285,8244039.91484128" "0.1" "" "0" "A0D-M-1694" "")
(command "_.insert" "INCRA_vertice_M" "204995.077117137,8244016.40173095" "0.1" "" "0" "A0D-M-1695" "")
(command "_.insert" "INCRA_vertice_M" "205016.668935724,8244040.22609313" "0.1" "" "0" "A0D-M-1696" "")
(command "_.insert" "INCRA_vertice_M" "205035.442860158,8244061.91965524" "0.1" "" "0" "A0D-M-1697" "")
(command "_.insert" "INCRA_vertice_M" "205032.239452152,8244109.19071389" "0.1" "" "0" "A0D-M-1698" "")
(command "_.insert" "INCRA_vertice_M" "205029.284935725,8244150.66409313" "0.1" "" "0" "A0D-M-1699" "")
(command "_.insert" "INCRA_vertice_M" "205028.251935725,8244165.05309313" "0.1" "" "0" "A0D-M-1700" "")
(command "_.insert" "INCRA_vertice_M" "205026.214935725,8244195.48009313" "0.1" "" "0" "A0D-M-1701" "")
(command "_.insert" "INCRA_vertice_M" "205025.371935725,8244197.98109313" "0.1" "" "0" "A0D-M-1702" "")
(command "_.insert" "INCRA_vertice_M" "205036.585148802,8244226.09309158" "0.1" "" "0" "A0D-M-1703" "")
(command "_.insert" "INCRA_vertice_M" "204878.502480695,8244397.45652685" "0.1" "" "0" "A0D-M-1704" "")
(command "_.insert" "INCRA_vertice_M" "204955.344856209,8244366.38845745" "0.1" "" "0" "A0D-M-1705" "")
(command "_.insert" "INCRA_vertice_M" "205073.430034995,8244319.26280831" "0.1" "" "0" "A0D-M-1706" "")
(command "_.insert" "INCRA_vertice_M" "205106.382828041,8244402.88247961" "0.1" "" "0" "A0D-M-1707" "")
(command "_.insert" "INCRA_vertice_M" "205104.48980808,8244408.42377377" "0.1" "" "0" "A0D-M-1708" "")
(command "_.insert" "INCRA_vertice_M" "205086.078935724,8244415.84509313" "0.1" "" "0" "A0D-M-1709" "")
(command "_.insert" "INCRA_vertice_M" "205070.525935724,8244422.01509313" "0.1" "" "0" "A0D-M-1710" "")
(command "_.insert" "INCRA_vertice_M" "205020.348935725,8244441.81509313" "0.1" "" "0" "A0D-M-1711" "")
(command "_.insert" "INCRA_vertice_M" "205005.896935725,8244447.58509313" "0.1" "" "0" "A0D-M-1712" "")
(command "_.insert" "INCRA_vertice_M" "205008.235935724,8244453.85009313" "0.1" "" "0" "A0D-M-1630" "")
(command "_.insert" "INCRA_vertice_M" "205097.804935725,8244421.30409313" "0.1" "" "0" "A0D-M-1631" "")
(command "_.insert" "INCRA_vertice_M" "205098.580935725,8244419.68709313" "0.1" "" "0" "A0D-M-1632" "")
(command "_.insert" "INCRA_vertice_M" "205099.914935725,8244419.55209313" "0.1" "" "0" "A0D-M-1633" "")
(command "_.insert" "INCRA_vertice_M" "205106.180935724,8244417.24209313" "0.1" "" "0" "A0D-M-1634" "")
(command "_.insert" "INCRA_vertice_M" "205106.966935725,8244416.11009313" "0.1" "" "0" "A0D-M-1635" "")
(command "_.insert" "INCRA_vertice_M" "205109.265935725,8244414.73609313" "0.1" "" "0" "A0D-M-1636" "")
(command "_.insert" "INCRA_vertice_M" "205112.494935725,8244409.60509313" "0.1" "" "0" "A0D-M-1637" "")
(command "_.insert" "INCRA_vertice_M" "205113.902935725,8244405.79509313" "0.1" "" "0" "A0D-M-1638" "")
(command "_.insert" "INCRA_vertice_M" "205115.296935725,8244398.37409313" "0.1" "" "0" "A0D-M-1639" "")
(command "_.insert" "INCRA_vertice_M" "205114.055935725,8244393.40109313" "0.1" "" "0" "A0D-M-1640" "")
(command "_.insert" "INCRA_vertice_M" "205112.001935725,8244389.73409312" "0.1" "" "0" "A0D-M-1641" "")
(command "_.insert" "INCRA_vertice_M" "205111.268935725,8244387.31809313" "0.1" "" "0" "A0D-M-1642" "")
(command "_.insert" "INCRA_vertice_M" "205104.178248359,8244366.33668737" "0.1" "" "0" "A0D-M-1643" "")
(command "_.insert" "INCRA_vertice_M" "205136.789269,8244353.246099" "0.1" "" "0" "A0D-M-1650" "")
(command "_.insert" "INCRA_vertice_M" "205244.082023874,8244310.17705984" "0.1" "" "0" "A0D-M-1651" "")
(command "_.insert" "INCRA_vertice_M" "205341.506,8244271.79899999" "0.1" "" "0" "A0D-M-1653" "")
(command "_.insert" "INCRA_vertice_M" "205402.385,8244247.75" "0.1" "" "0" "A0D-M-1654" "")
(command "_.insert" "INCRA_vertice_M" "205438.814321658,8244278.67097656" "0.1" "" "0" "A0D-M-1655" "")
(command "_.insert" "INCRA_vertice_M" "205456.854550524,8244295.54793834" "0.1" "" "0" "A0D-M-1656" "")
(command "_.insert" "INCRA_vertice_M" "205477.820077273,8244316.75090186" "0.1" "" "0" "A0D-M-1657" "")
(command "_.insert" "INCRA_vertice_M" "205509.603365598,8244406.40924886" "0.1" "" "0" "A0D-M-1658" "")
(command "_.layer" "m" "VERTICES_TIPO_V" "")
(command "_.insert" "INCRA_vertice_V" "205556.415396666,8244508.53328534" "0.1" "" "0" "A0D-V-5150" "")
(command "_.insert" "INCRA_vertice_V" "206095.497745561,8244387.92150499" "0.1" "" "0" "A0D-V-5156" "")
(command "_.insert" "INCRA_vertice_V" "206195.970935725,8244369.24809313" "0.1" "" "0" "A0D-V-5157" "")
(command "_.insert" "INCRA_vertice_V" "206215.167526242,8244202.66843178" "0.1" "" "0" "A0D-V-5158" "")
(command "_.insert" "INCRA_vertice_V" "206361.650249482,8243877.03855365" "0.1" "" "0" "A0D-V-5159" "")
(command "_.insert" "INCRA_vertice_V" "206331.693935725,8243762.95109312" "0.1" "" "0" "A0D-V-5160" "")
(command "_.insert" "INCRA_vertice_V" "206149.112952718,8243622.08759567" "0.1" "" "0" "A0D-V-5161" "")
(command "_.insert" "INCRA_vertice_V" "206042.389527831,8243587.83324536" "0.1" "" "0" "A0D-V-5162" "")
(command "_.insert" "INCRA_vertice_V" "204339.899790524,8243523.30006466" "0.1" "" "0" "A0D-V-5163" "")
(command "_.insert" "INCRA_vertice_V" "204771.020106219,8244103.8256972" "0.1" "" "0" "A0D-V-5164" "")
(command "_.insert" "INCRA_vertice_V" "204853.785320675,8244301.83598091" "0.1" "" "0" "A0D-V-5165" "")
(command "_.insert" "INCRA_vertice_V" "205462.274008504,8244500.89060974" "0.1" "" "0" "A0D-V-5166" "")
(command "_.insert" "INCRA_vertice_V" "205556.415396666,8244508.53328534" "0.1" "" "0" "A0D-V-5150" "")
(command "_.layer" "m" "VERTICES_TIPO_P" "")(command "_.insert" "INCRA_vertice_P" "206101.412935725,8244386.36809312" "0.1" "" "0" "A0D-P-5236" "")
(command "_.insert" "INCRA_vertice_P" "206113.458935725,8244387.56409312" "0.1" "" "0" "A0D-P-5237" "")
(command "_.insert" "INCRA_vertice_P" "206136.110935725,8244389.25009313" "0.1" "" "0" "A0D-P-5238" "")
(command "_.insert" "INCRA_vertice_P" "206145.354935724,8244386.45409312" "0.1" "" "0" "A0D-P-5239" "")
(command "_.insert" "INCRA_vertice_P" "206157.911935724,8244387.00309313" "0.1" "" "0" "A0D-P-5240" "")
(command "_.insert" "INCRA_vertice_P" "206176.277935725,8244391.25909313" "0.1" "" "0" "A0D-P-5241" "")
(command "_.insert" "INCRA_vertice_P" "206188.106935725,8244395.15209313" "0.1" "" "0" "A0D-P-5242" "")
(command "_.insert" "INCRA_vertice_P" "206191.520935725,8244381.58609313" "0.1" "" "0" "A0D-P-5243" "")
(command "_.insert" "INCRA_vertice_P" "206199.49592989,8244176.78883931" "0.1" "" "0" "A0D-P-5244" "")
(command "_.insert" "INCRA_vertice_P" "206190.849935725,8244161.05509313" "0.1" "" "0" "A0D-P-5245" "")
(command "_.insert" "INCRA_vertice_P" "206185.213935725,8244150.13909313" "0.1" "" "0" "A0D-P-5246" "")
(command "_.insert" "INCRA_vertice_P" "206182.639935725,8244139.09809313" "0.1" "" "0" "A0D-P-5247" "")
(command "_.insert" "INCRA_vertice_P" "206188.066935725,8244132.30309312" "0.1" "" "0" "A0D-P-5248" "")
(command "_.insert" "INCRA_vertice_P" "206196.833935725,8244129.00109313" "0.1" "" "0" "A0D-P-5249" "")
(command "_.insert" "INCRA_vertice_P" "206208.665935724,8244122.68209313" "0.1" "" "0" "A0D-P-5250" "")
(command "_.insert" "INCRA_vertice_P" "206195.045935725,8244082.63709313" "0.1" "" "0" "A0D-P-5251" "")
(command "_.insert" "INCRA_vertice_P" "206182.697935724,8244041.40909313" "0.1" "" "0" "A0D-P-5252" "")
(command "_.insert" "INCRA_vertice_P" "206180.181935725,8244031.79409313" "0.1" "" "0" "A0D-P-5253" "")
(command "_.insert" "INCRA_vertice_P" "206177.415935725,8244019.61409313" "0.1" "" "0" "A0D-P-5254" "")
(command "_.insert" "INCRA_vertice_P" "206178.938935724,8244007.64109313" "0.1" "" "0" "A0D-P-5255" "")
(command "_.insert" "INCRA_vertice_P" "206181.693935725,8244002.37509313" "0.1" "" "0" "A0D-P-5256" "")
(command "_.insert" "INCRA_vertice_P" "206193.537935725,8244004.55809313" "0.1" "" "0" "A0D-P-5257" "")
(command "_.insert" "INCRA_vertice_P" "206201.862935724,8244010.95409313" "0.1" "" "0" "A0D-P-5258" "")
(command "_.insert" "INCRA_vertice_P" "206213.590935724,8244020.56909313" "0.1" "" "0" "A0D-P-5259" "")
(command "_.insert" "INCRA_vertice_P" "206217.100935725,8244030.10409312" "0.1" "" "0" "A0D-P-5260" "")
(command "_.insert" "INCRA_vertice_P" "206223.426935724,8244034.05309313" "0.1" "" "0" "A0D-P-5261" "")
(command "_.insert" "INCRA_vertice_P" "206237.817935724,8244036.31009313" "0.1" "" "0" "A0D-P-5262" "")
(command "_.insert" "INCRA_vertice_P" "206258.639935724,8244038.26409313" "0.1" "" "0" "A0D-P-5263" "")
(command "_.insert" "INCRA_vertice_P" "206269.265935724,8244033.49309313" "0.1" "" "0" "A0D-P-5264" "")
(command "_.insert" "INCRA_vertice_P" "206283.064935725,8244014.20709313" "0.1" "" "0" "A0D-P-5265" "")
(command "_.insert" "INCRA_vertice_P" "206287.480935725,8243996.36809313" "0.1" "" "0" "A0D-P-5266" "")
(command "_.insert" "INCRA_vertice_P" "206300.512935725,8243983.22009312" "0.1" "" "0" "A0D-P-5267" "")
(command "_.insert" "INCRA_vertice_P" "206313.741935725,8243976.73509312" "0.1" "" "0" "A0D-P-5268" "")
(command "_.insert" "INCRA_vertice_P" "206329.818935724,8243973.33809313" "0.1" "" "0" "A0D-P-5269" "")
(command "_.insert" "INCRA_vertice_P" "206360.543935725,8243940.65309313" "0.1" "" "0" "A0D-P-5270" "")
(command "_.insert" "INCRA_vertice_P" "206366.351935725,8243923.38309312" "0.1" "" "0" "A0D-P-5271" "")
(command "_.insert" "INCRA_vertice_P" "206367.454935725,8243901.53909313" "0.1" "" "0" "A0D-P-5272" "")
(command "_.insert" "INCRA_vertice_P" "206362.873534587,8243879.3169031" "0.1" "" "0" "A0D-P-5273" "")
(command "_.insert" "INCRA_vertice_P" "206311.867993984,8243709.74994163" "0.1" "" "0" "CWM-P-A302" "")
(command "_.insert" "INCRA_vertice_P" "206307.42375951,8243680.80614986" "0.1" "" "0" "CWM-P-A301" "")
(command "_.insert" "INCRA_vertice_P" "206295.471241065,8243654.56464252" "0.1" "" "0" "CWM-P-A300" "")
(command "_.insert" "INCRA_vertice_P" "206292.724085133,8243627.88888982" "0.1" "" "0" "CWM-P-A299" "")
(command "_.insert" "INCRA_vertice_P" "206281.893272446,8243609.13705332" "0.1" "" "0" "CWM-P-A298" "")
(command "_.insert" "INCRA_vertice_P" "206269.959658942,8243597.41386852" "0.1" "" "0" "CWM-P-A297" "")
(command "_.insert" "INCRA_vertice_P" "206247.400931566,8243589.85929378" "0.1" "" "0" "CWM-P-A296" "")
(command "_.insert" "INCRA_vertice_P" "206238.638623623,8243590.51304018" "0.1" "" "0" "CWM-P-A295" "")
(command "_.insert" "INCRA_vertice_P" "206229.281647822,8243595.65063533" "0.1" "" "0" "CWM-P-A294" "")
(command "_.insert" "INCRA_vertice_P" "206198.736414215,8243620.50595885" "0.1" "" "0" "CWM-P-A293" "")
(command "_.insert" "INCRA_vertice_P" "206187.275562179,8243627.18406277" "0.1" "" "0" "CWM-P-A292" "")
(command "_.insert" "INCRA_vertice_P" "206177.521426678,8243630.80925539" "0.1" "" "0" "CWM-P-A291" "")
(command "_.insert" "INCRA_vertice_P" "206134.919098939,8243616.96208147" "0.1" "" "0" "CWM-P-A290" "")
(command "_.insert" "INCRA_vertice_P" "206114.624495644,8243607.00628105" "0.1" "" "0" "CWM-P-A289" "")
(command "_.insert" "INCRA_vertice_P" "206082.317554924,8243602.70689845" "0.1" "" "0" "CWM-P-A288" "")
(command "_.insert" "INCRA_vertice_P" "206068.871684616,8243599.48527339" "0.1" "" "0" "CWM-P-A287" "")
(command "_.insert" "INCRA_vertice_P" "206025.102698067,8243579.22396716" "0.1" "" "0" "CWM-P-A286" "")
(command "_.insert" "INCRA_vertice_P" "206002.245484939,8243564.92773868" "0.1" "" "0" "CWM-P-A285" "")
(command "_.insert" "INCRA_vertice_P" "205993.694653733,8243542.66743695" "0.1" "" "0" "CWM-P-A284" "")
(command "_.insert" "INCRA_vertice_P" "205975.58872313,8243536.15543676" "0.1" "" "0" "CWM-P-A283" "")
(command "_.insert" "INCRA_vertice_P" "205946.204387279,8243538.2617657" "0.1" "" "0" "CWM-P-A282" "")
(command "_.insert" "INCRA_vertice_P" "205844.072193048,8243538.95200201" "0.1" "" "0" "CWM-P-A281" "")
(command "_.insert" "INCRA_vertice_P" "205810.987748745,8243546.20890853" "0.1" "" "0" "CWM-P-A280" "")
(command "_.insert" "INCRA_vertice_P" "205797.991810343,8243551.91320652" "0.1" "" "0" "CWM-P-A279" "")
(command "_.insert" "INCRA_vertice_P" "205762.408274793,8243579.47043312" "0.1" "" "0" "CWM-P-A278" "")
(command "_.insert" "INCRA_vertice_P" "205743.898461527,8243599.16093602" "0.1" "" "0" "CWM-P-A277" "")
(command "_.insert" "INCRA_vertice_P" "205728.388033213,8243612.61509152" "0.1" "" "0" "CWM-P-A276" "")
(command "_.insert" "INCRA_vertice_P" "205720.707690524,8243617.06686476" "0.1" "" "0" "CWM-P-A275" "")
(command "_.insert" "INCRA_vertice_P" "205704.197543871,8243622.81802168" "0.1" "" "0" "CWM-P-A274" "")
(command "_.insert" "INCRA_vertice_P" "205688.662847608,8243638.11789341" "0.1" "" "0" "CWM-P-A273" "")
(command "_.insert" "INCRA_vertice_P" "205675.903240305,8243646.22499857" "0.1" "" "0" "CWM-P-A272" "")
(command "_.insert" "INCRA_vertice_P" "205666.701769291,8243648.56489014" "0.1" "" "0" "CWM-P-A271" "")
(command "_.insert" "INCRA_vertice_P" "205624.990348244,8243641.64972262" "0.1" "" "0" "CWM-P-A270" "")
(command "_.insert" "INCRA_vertice_P" "205611.403714519,8243635.5965303" "0.1" "" "0" "CWM-P-A269" "")
(command "_.insert" "INCRA_vertice_P" "205602.539207757,8243628.19005309" "0.1" "" "0" "CWM-P-A268" "")
(command "_.insert" "INCRA_vertice_P" "205571.584725083,8243593.45383089" "0.1" "" "0" "CWM-P-A267" "")
(command "_.insert" "INCRA_vertice_P" "205546.943835024,8243574.36515008" "0.1" "" "0" "CWM-P-A266" "")
(command "_.insert" "INCRA_vertice_P" "205532.700486525,8243563.96553763" "0.1" "" "0" "CWM-P-A265" "")
(command "_.insert" "INCRA_vertice_P" "205516.355628475,8243558.96390643" "0.1" "" "0" "A0D-P-0842" "")
(command "_.insert" "INCRA_vertice_P" "205515.661355218,8243559.90541896" "0.1" "" "0" "A0D-P-0841" "")
(command "_.insert" "INCRA_vertice_P" "205508.997825441,8243573.8032395" "0.1" "" "0" "A0D-P-0840" "")
(command "_.insert" "INCRA_vertice_P" "205507.171847339,8243574.4708746" "0.1" "" "0" "A0D-P-0839" "")
(command "_.insert" "INCRA_vertice_P" "205499.699027655,8243567.91135262" "0.1" "" "0" "A0D-P-0838" "")
(command "_.insert" "INCRA_vertice_P" "205493.590694689,8243566.09913944" "0.1" "" "0" "A0D-P-0837" "")
(command "_.insert" "INCRA_vertice_P" "205489.561689661,8243570.23795337" "0.1" "" "0" "A0D-P-0836" "")
(command "_.insert" "INCRA_vertice_P" "205485.556232015,8243578.62424021" "0.1" "" "0" "A0D-P-0835" "")
(command "_.insert" "INCRA_vertice_P" "205480.716910141,8243580.44118739" "0.1" "" "0" "A0D-P-0834" "")
(command "_.insert" "INCRA_vertice_P" "205472.674371535,8243586.7056019" "0.1" "" "0" "A0D-P-0833" "")
(command "_.insert" "INCRA_vertice_P" "205469.237937658,8243592.27914226" "0.1" "" "0" "A0D-P-0832" "")
(command "_.insert" "INCRA_vertice_P" "205465.480923646,8243591.6825551" "0.1" "" "0" "A0D-P-0831" "")
(command "_.insert" "INCRA_vertice_P" "205453.678617993,8243589.28797355" "0.1" "" "0" "A0D-P-0830" "")
(command "_.insert" "INCRA_vertice_P" "205446.403278409,8243590.00621621" "0.1" "" "0" "A0D-P-0829" "")
(command "_.insert" "INCRA_vertice_P" "205431.426423963,8243592.95683436" "0.1" "" "0" "A0D-P-0828" "")
(command "_.insert" "INCRA_vertice_P" "205413.865044646,8243608.39758666" "0.1" "" "0" "A0D-P-0827" "")
(command "_.insert" "INCRA_vertice_P" "205407.130611747,8243618.48580793" "0.1" "" "0" "A0D-P-0826" "")
(command "_.insert" "INCRA_vertice_P" "205402.428754127,8243621.10277533" "0.1" "" "0" "A0D-P-0825" "")
(command "_.insert" "INCRA_vertice_P" "205394.837288721,8243624.74541494" "0.1" "" "0" "A0D-P-0824" "")
(command "_.insert" "INCRA_vertice_P" "205391.963671819,8243624.74651005" "0.1" "" "0" "A0D-P-0823" "")
(command "_.insert" "INCRA_vertice_P" "205386.285675099,8243626.21732058" "0.1" "" "0" "A0D-P-0822" "")
(command "_.insert" "INCRA_vertice_P" "205380.271891149,8243625.34471238" "0.1" "" "0" "A0D-P-0821" "")
(command "_.insert" "INCRA_vertice_P" "205378.412927207,8243631.24990493" "0.1" "" "0" "A0D-P-0820" "")
(command "_.insert" "INCRA_vertice_P" "205378.025408411,8243637.80595494" "0.1" "" "0" "A0D-P-0819" "")
(command "_.insert" "INCRA_vertice_P" "205375.163152204,8243637.82378912" "0.1" "" "0" "A0D-P-0818" "")
(command "_.insert" "INCRA_vertice_P" "205370.659728867,8243639.10885761" "0.1" "" "0" "A0D-P-0817" "")
(command "_.insert" "INCRA_vertice_P" "205369.941126708,8243640.40958566" "0.1" "" "0" "A0D-P-0816" "")
(command "_.insert" "INCRA_vertice_P" "205364.834809962,8243640.01954981" "0.1" "" "0" "A0D-P-0815" "")
(command "_.insert" "INCRA_vertice_P" "205361.997024985,8243639.64015708" "0.1" "" "0" "A0D-P-0814" "")
(command "_.insert" "INCRA_vertice_P" "205352.898414052,8243644.15063862" "0.1" "" "0" "A0D-P-0813" "")
(command "_.insert" "INCRA_vertice_P" "205350.728423192,8243647.07351139" "0.1" "" "0" "A0D-P-0812" "")
(command "_.insert" "INCRA_vertice_P" "205352.025063706,8243653.83978249" "0.1" "" "0" "A0D-P-0811" "")
(command "_.insert" "INCRA_vertice_P" "205349.048437469,8243653.6863433" "0.1" "" "0" "A0D-P-0810" "")
(command "_.insert" "INCRA_vertice_P" "205347.295464981,8243654.00221588" "0.1" "" "0" "A0D-P-0809" "")
(command "_.insert" "INCRA_vertice_P" "205335.96125368,8243654.17168819" "0.1" "" "0" "A0D-P-0808" "")
(command "_.insert" "INCRA_vertice_P" "205313.090839345,8243651.3621355" "0.1" "" "0" "A0D-P-0807" "")
(command "_.insert" "INCRA_vertice_P" "205306.989586807,8243659.76080152" "0.1" "" "0" "A0D-P-0806" "")
(command "_.insert" "INCRA_vertice_P" "205296.769802534,8243657.48248409" "0.1" "" "0" "A0D-P-0805" "")
(command "_.insert" "INCRA_vertice_P" "205285.182018422,8243658.22609511" "0.1" "" "0" "A0D-P-0804" "")
(command "_.insert" "INCRA_vertice_P" "205270.125113168,8243656.62515972" "0.1" "" "0" "A0D-P-0803" "")
(command "_.insert" "INCRA_vertice_P" "205264.021726324,8243656.07092921" "0.1" "" "0" "A0D-P-0802" "")
(command "_.insert" "INCRA_vertice_P" "205253.725752282,8243655.83029116" "0.1" "" "0" "A0D-P-0801" "")
(command "_.insert" "INCRA_vertice_P" "205243.408273543,8243653.01611715" "0.1" "" "0" "A0D-P-0800" "")
(command "_.insert" "INCRA_vertice_P" "205234.262838212,8243651.75027181" "0.1" "" "0" "A0D-P-0799" "")
(command "_.insert" "INCRA_vertice_P" "205221.898541083,8243648.23010557" "0.1" "" "0" "A0D-P-0798" "")
(command "_.insert" "INCRA_vertice_P" "205202.91185235,8243645.08419961" "0.1" "" "0" "A0D-P-0797" "")
(command "_.insert" "INCRA_vertice_P" "205188.049385322,8243647.96132054" "0.1" "" "0" "A0D-P-0796" "")
(command "_.insert" "INCRA_vertice_P" "205176.340025285,8243649.7551674" "0.1" "" "0" "A0D-P-0795" "")
(command "_.insert" "INCRA_vertice_P" "205168.136627262,8243657.44529644" "0.1" "" "0" "A0D-P-0794" "")
(command "_.insert" "INCRA_vertice_P" "205159.335375136,8243651.99248391" "0.1" "" "0" "A0D-P-0793" "")
(command "_.insert" "INCRA_vertice_P" "205149.793779029,8243651.72441459" "0.1" "" "0" "A0D-P-0792" "")
(command "_.insert" "INCRA_vertice_P" "205138.435772836,8243656.29753467" "0.1" "" "0" "A0D-P-0791" "")
(command "_.insert" "INCRA_vertice_P" "205133.078009273,8243653.2617332" "0.1" "" "0" "A0D-P-0790" "")
(command "_.insert" "INCRA_vertice_P" "205127.375630375,8243644.12424429" "0.1" "" "0" "A0D-P-0789" "")
(command "_.insert" "INCRA_vertice_P" "205107.015500619,8243639.3438449" "0.1" "" "0" "A0D-P-0788" "")
(command "_.insert" "INCRA_vertice_P" "205091.897251543,8243642.21740976" "0.1" "" "0" "A0D-P-0787" "")
(command "_.insert" "INCRA_vertice_P" "205077.57712949,8243637.15239277" "0.1" "" "0" "A0D-P-0786" "")
(command "_.insert" "INCRA_vertice_P" "205071.390345544,8243641.34996471" "0.1" "" "0" "A0D-P-0785" "")
(command "_.insert" "INCRA_vertice_P" "205056.784222323,8243637.84213048" "0.1" "" "0" "A0D-P-0784" "")
(command "_.insert" "INCRA_vertice_P" "205040.676494561,8243639.07793546" "0.1" "" "0" "A0D-P-0783" "")
(command "_.insert" "INCRA_vertice_P" "205022.647670857,8243632.38864597" "0.1" "" "0" "A0D-P-0782" "")
(command "_.insert" "INCRA_vertice_P" "205009.344294323,8243627.66316204" "0.1" "" "0" "A0D-P-0781" "")
(command "_.insert" "INCRA_vertice_P" "204997.25700743,8243628.2322528" "0.1" "" "0" "A0D-P-0780" "")
(command "_.insert" "INCRA_vertice_P" "204989.760986143,8243621.07008974" "0.1" "" "0" "A0D-P-0779" "")
(command "_.insert" "INCRA_vertice_P" "204978.559675678,8243620.4424856" "0.1" "" "0" "A0D-P-0778" "")
(command "_.insert" "INCRA_vertice_P" "204960.786725781,8243623.19003834" "0.1" "" "0" "A0D-P-0777" "")
(command "_.insert" "INCRA_vertice_P" "204948.890254157,8243616.01820966" "0.1" "" "0" "A0D-P-0776" "")
(command "_.insert" "INCRA_vertice_P" "204936.40447353,8243618.24527635" "0.1" "" "0" "A0D-P-0775" "")
(command "_.insert" "INCRA_vertice_P" "204920.471107521,8243621.6273227" "0.1" "" "0" "A0D-P-0774" "")
(command "_.insert" "INCRA_vertice_P" "204907.480300325,8243615.49286193" "0.1" "" "0" "A0D-P-0773" "")
(command "_.insert" "INCRA_vertice_P" "204892.380216814,8243615.43865481" "0.1" "" "0" "A0D-P-0772" "")
(command "_.insert" "INCRA_vertice_P" "204886.777160367,8243618.44891977" "0.1" "" "0" "A0D-P-0771" "")
(command "_.insert" "INCRA_vertice_P" "204882.604889176,8243614.01451857" "0.1" "" "0" "A0D-P-0770" "")
(command "_.insert" "INCRA_vertice_P" "204875.394801755,8243606.09229259" "0.1" "" "0" "A0D-P-0769" "")
(command "_.insert" "INCRA_vertice_P" "204863.286075767,8243601.44615941" "0.1" "" "0" "A0D-P-0768" "")
(command "_.insert" "INCRA_vertice_P" "204852.037541937,8243597.56255983" "0.1" "" "0" "A0D-P-0767" "")
(command "_.insert" "INCRA_vertice_P" "204837.064314047,8243593.66537001" "0.1" "" "0" "A0D-P-0766" "")
(command "_.insert" "INCRA_vertice_P" "204823.74683578,8243583.07487414" "0.1" "" "0" "A0D-P-0765" "")
(command "_.insert" "INCRA_vertice_P" "204814.334529011,8243581.17205272" "0.1" "" "0" "A0D-P-0764" "")
(command "_.insert" "INCRA_vertice_P" "204806.438508048,8243581.36362056" "0.1" "" "0" "A0D-P-0763" "")
(command "_.insert" "INCRA_vertice_P" "204798.772473096,8243576.57860736" "0.1" "" "0" "A0D-P-0762" "")
(command "_.insert" "INCRA_vertice_P" "204790.347496757,8243572.01757631" "0.1" "" "0" "A0D-P-0761" "")
(command "_.insert" "INCRA_vertice_P" "204778.694699663,8243568.99311623" "0.1" "" "0" "A0D-P-0760" "")
(command "_.insert" "INCRA_vertice_P" "204760.397696749,8243566.29257689" "0.1" "" "0" "A0D-P-0759" "")
(command "_.insert" "INCRA_vertice_P" "204749.732286723,8243569.270607" "0.1" "" "0" "A0D-P-0758" "")
(command "_.insert" "INCRA_vertice_P" "204734.542230259,8243563.46201798" "0.1" "" "0" "A0D-P-0757" "")
(command "_.insert" "INCRA_vertice_P" "204725.674054135,8243557.11574438" "0.1" "" "0" "A0D-P-0756" "")
(command "_.insert" "INCRA_vertice_P" "204715.41,8243551.37" "0.1" "" "0" "A0D-P-0755" "")
(command "_.insert" "INCRA_vertice_P" "204702.7,8243545.65" "0.1" "" "0" "A0D-P-0754" "")
(command "_.insert" "INCRA_vertice_P" "204696.200348584,8243543.16583648" "0.1" "" "0" "A0D-P-0753" "")
(command "_.insert" "INCRA_vertice_P" "204691.835927013,8243541.4451513" "0.1" "" "0" "A0D-P-0752" "")
(command "_.insert" "INCRA_vertice_P" "204686.77380643,8243540.9861588" "0.1" "" "0" "A0D-P-0751" "")
(command "_.insert" "INCRA_vertice_P" "204667.410430422,8243537.49827914" "0.1" "" "0" "A0D-P-0750" "")
(command "_.insert" "INCRA_vertice_P" "204650.724093066,8243535.81139216" "0.1" "" "0" "A0D-P-0749" "")
(command "_.insert" "INCRA_vertice_P" "204636.444337594,8243539.73627033" "0.1" "" "0" "A0D-P-0748" "")
(command "_.insert" "INCRA_vertice_P" "204625.130752574,8243536.69841961" "0.1" "" "0" "A0D-P-0747" "")
(command "_.insert" "INCRA_vertice_P" "204609.616930434,8243539.34535252" "0.1" "" "0" "A0D-P-0746" "")
(command "_.insert" "INCRA_vertice_P" "204599.441823404,8243541.97642468" "0.1" "" "0" "A0D-P-0745" "")
(command "_.insert" "INCRA_vertice_P" "204585.692770442,8243537.80262486" "0.1" "" "0" "A0D-P-0744" "")
(command "_.insert" "INCRA_vertice_P" "204568.21342241,8243540.77523494" "0.1" "" "0" "A0D-P-0743" "")
(command "_.insert" "INCRA_vertice_P" "204555.619011389,8243544.52247201" "0.1" "" "0" "A0D-P-0742" "")
(command "_.insert" "INCRA_vertice_P" "204543.325571626,8243545.62972133" "0.1" "" "0" "A0D-P-0741" "")
(command "_.insert" "INCRA_vertice_P" "204532.014246131,8243539.87213095" "0.1" "" "0" "A0D-P-0740" "")
(command "_.insert" "INCRA_vertice_P" "204512.581049963,8243538.16189777" "0.1" "" "0" "A0D-P-0739" "")
(command "_.insert" "INCRA_vertice_P" "204501.999927032,8243533.39135603" "0.1" "" "0" "A0D-P-0738" "")
(command "_.insert" "INCRA_vertice_P" "204487.326590034,8243529.31855541" "0.1" "" "0" "A0D-P-0737" "")
(command "_.insert" "INCRA_vertice_P" "204463.391935725,8243525.59109313" "0.1" "" "0" "A0D-P-0736" "")
(command "_.insert" "INCRA_vertice_P" "204456.421176722,8243519.99063706" "0.1" "" "0" "A0D-P-0735" "")
(command "_.insert" "INCRA_vertice_P" "204447.857732473,8243515.93408179" "0.1" "" "0" "A0D-P-0734" "")
(command "_.insert" "INCRA_vertice_P" "204439.319508498,8243513.82085331" "0.1" "" "0" "A0D-P-0733" "")
(command "_.insert" "INCRA_vertice_P" "204426.275861204,8243515.9650969" "0.1" "" "0" "A0D-P-0732" "")
(command "_.insert" "INCRA_vertice_P" "204415.280627171,8243513.98699623" "0.1" "" "0" "A0D-P-0731" "")
(command "_.insert" "INCRA_vertice_P" "204406.618158753,8243509.15469709" "0.1" "" "0" "A0D-P-0730" "")
(command "_.insert" "INCRA_vertice_P" "204397.113906656,8243506.23496633" "0.1" "" "0" "A0D-P-0729" "")
(command "_.insert" "INCRA_vertice_P" "204388.108850326,8243504.81829755" "0.1" "" "0" "A0D-P-0728" "")
(command "_.insert" "INCRA_vertice_P" "204382.69004211,8243504.70233784" "0.1" "" "0" "A0D-P-0727" "")
(command "_.insert" "INCRA_vertice_P" "204378.586177372,8243509.00101324" "0.1" "" "0" "A0D-P-0726" "")
(command "_.insert" "INCRA_vertice_P" "204379.094163769,8243510.00986074" "0.1" "" "0" "A0D-P-0725" "")
(command "_.insert" "INCRA_vertice_P" "204351.676174009,8243532.95274459" "0.1" "" "0" "A0D-P-5392" "")
(command "_.insert" "INCRA_vertice_P" "204368.112396273,8243548.9100385" "0.1" "" "0" "A0D-P-5393" "")
(command "_.insert" "INCRA_vertice_P" "204373.688077196,8243551.74790258" "0.1" "" "0" "A0D-P-5394" "")
(command "_.insert" "INCRA_vertice_P" "204417.739615797,8243592.76921323" "0.1" "" "0" "A0D-P-5395" "")
(command "_.insert" "INCRA_vertice_P" "204472.99234834,8243648.27998267" "0.1" "" "0" "A0D-P-5396" "")
(command "_.insert" "INCRA_vertice_P" "204481.361632576,8243656.96195335" "0.1" "" "0" "A0D-P-5397" "")
(command "_.insert" "INCRA_vertice_P" "204485.597528905,8243662.32487231" "0.1" "" "0" "A0D-P-5398" "")
(command "_.insert" "INCRA_vertice_P" "204487.538218742,8243664.97837664" "0.1" "" "0" "A0D-P-5399" "")
(command "_.insert" "INCRA_vertice_P" "204490.616841855,8243669.91746777" "0.1" "" "0" "A0D-P-5400" "")
(command "_.insert" "INCRA_vertice_P" "204532.889094809,8243712.94266377" "0.1" "" "0" "A0D-P-5000" "")
(command "_.insert" "INCRA_vertice_P" "204538.320108561,8243714.88210459" "0.1" "" "0" "A0D-P-5401" "")
(command "_.insert" "INCRA_vertice_P" "204544.533060797,8243717.10077936" "0.1" "" "0" "A0D-P-5402" "")
(command "_.insert" "INCRA_vertice_P" "204551.508851196,8243718.68674766" "0.1" "" "0" "A0D-P-5403" "")
(command "_.insert" "INCRA_vertice_P" "204568.424286194,8243719.2210488" "0.1" "" "0" "A0D-P-5404" "")
(command "_.insert" "INCRA_vertice_P" "204576.197598269,8243719.27757287" "0.1" "" "0" "A0D-P-5405" "")
(command "_.insert" "INCRA_vertice_P" "204593.789076897,8243719.87349243" "0.1" "" "0" "A0D-P-5406" "")
(command "_.insert" "INCRA_vertice_P" "204605.601441433,8243720.951581" "0.1" "" "0" "A0D-P-5407" "")
(command "_.insert" "INCRA_vertice_P" "204616.876213508,8243721.93854174" "0.1" "" "0" "A0D-P-5408" "")
(command "_.insert" "INCRA_vertice_P" "204629.501979046,8243723.68719249" "0.1" "" "0" "A0D-P-5409" "")
(command "_.insert" "INCRA_vertice_P" "204629.290521566,8243730.23910547" "0.1" "" "0" "A0D-P-5410" "")
(command "_.insert" "INCRA_vertice_P" "204625.657128901,8243735.70025039" "0.1" "" "0" "A0D-P-5411" "")
(command "_.insert" "INCRA_vertice_P" "204624.800514836,8243744.68379792" "0.1" "" "0" "A0D-P-5412" "")
(command "_.insert" "INCRA_vertice_P" "204623.081916771,8243747.58007837" "0.1" "" "0" "A0D-P-5413" "")
(command "_.insert" "INCRA_vertice_P" "204616.661244915,8243756.28463594" "0.1" "" "0" "A0D-P-5414" "")
(command "_.insert" "INCRA_vertice_P" "204613.392935725,8243762.68709313" "0.1" "" "0" "A0D-P-5415" "")
(command "_.insert" "INCRA_vertice_P" "204600.567935725,8243778.62309313" "0.1" "" "0" "A0D-P-5416" "")
(command "_.insert" "INCRA_vertice_P" "204596.315337719,8243787.27394105" "0.1" "" "0" "A0D-P-5417" "")
(command "_.insert" "INCRA_vertice_P" "204580.914852797,8243814.66923982" "0.1" "" "0" "A0D-P-5418" "")
(command "_.insert" "INCRA_vertice_P" "204596.086702388,8243833.06171" "0.1" "" "0" "A0D-P-5419" "")
(command "_.insert" "INCRA_vertice_P" "204606.834933906,8243853.46125755" "0.1" "" "0" "A0D-P-5420" "")
(command "_.insert" "INCRA_vertice_P" "204615.890760493,8243865.33261723" "0.1" "" "0" "A0D-P-5421" "")
(command "_.insert" "INCRA_vertice_P" "204632.819935452,8243886.01422209" "0.1" "" "0" "A0D-P-5422" "")
(command "_.insert" "INCRA_vertice_P" "204649.343697111,8243905.81462331" "0.1" "" "0" "A0D-P-5423" "")
(command "_.insert" "INCRA_vertice_P" "204672.114386975,8243936.81033826" "0.1" "" "0" "A0D-P-5424" "")
(command "_.insert" "INCRA_vertice_P" "204679.641773308,8243950.01747251" "0.1" "" "0" "A0D-P-5425" "")
(command "_.insert" "INCRA_vertice_P" "204691.805918925,8243966.72176793" "0.1" "" "0" "A0D-P-5426" "")
(command "_.insert" "INCRA_vertice_P" "204707.657557782,8243987.79191493" "0.1" "" "0" "A0D-P-5427" "")
(command "_.insert" "INCRA_vertice_P" "204725.469714028,8244007.60673747" "0.1" "" "0" "A0D-P-5428" "")
(command "_.insert" "INCRA_vertice_P" "204739.935371999,8244026.40209012" "0.1" "" "0" "A0D-P-5429" "")
(command "_.insert" "INCRA_vertice_P" "204752.798050981,8244048.73570348" "0.1" "" "0" "A0D-P-5430" "")
(command "_.insert" "INCRA_vertice_P" "204759.488935725,8244078.56709312" "0.1" "" "0" "A0D-P-5431" "")
(command "_.insert" "INCRA_vertice_P" "204863.355171569,8244319.00711999" "0.1" "" "0" "A0D-P-5432" "")
(command "_.insert" "INCRA_vertice_P" "204879.675769053,8244332.92385988" "0.1" "" "0" "A0D-P-5433" "")
(command "_.insert" "INCRA_vertice_P" "204887.877651612,8244345.54099954" "0.1" "" "0" "A0D-P-5434" "")
(command "_.insert" "INCRA_vertice_P" "204889.887561749,8244353.54481614" "0.1" "" "0" "A0D-P-5435" "")
(command "_.insert" "INCRA_vertice_P" "204889.213326263,8244363.76866469" "0.1" "" "0" "A0D-P-5436" "")
(command "_.insert" "INCRA_vertice_P" "204883.389999999,8244388.1" "0.1" "" "0" "A0D-P-5437" "")
(command "_.insert" "INCRA_vertice_P" "205466.081529937,8244495.87803461" "0.1" "" "0" "A0D-P-5230" "")
(command "_.insert" "INCRA_vertice_P" "205478.957719039,8244488.61335495" "0.1" "" "0" "A0D-P-5231" "")
(command "_.insert" "INCRA_vertice_P" "205495.196460265,8244484.01431889" "0.1" "" "0" "A0D-P-5232" "")
(command "_.insert" "INCRA_vertice_P" "205506.942276952,8244485.32654495" "0.1" "" "0" "A0D-P-5233" "")
(command "_.insert" "INCRA_vertice_P" "205526.055935724,8244491.21509313" "0.1" "" "0" "A0D-P-5234" "")
(command "_.insert" "INCRA_vertice_P" "205544.76990364,8244501.87076775" "0.1" "" "0" "A0D-P-5235" "")
(setvar "cmdecho" olcmdecho)
(setvar "clayer" oldlayer)
(princ)
)
(princ "\nDigite 'belvedere' para iniciar")
