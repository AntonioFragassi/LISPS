;; Coloca numero da estaca com numeração sequencial

(defun c:NESTACA ( / oldlayer Ht regua Delta oldosmode olcmdecho escala ponto i PONTO DESC COTA)
  (setq oldlayer (getvar "clayer"))
  (setq oldosmode (getvar "osmode"))
  (setvar "osmode" 0)
  (setq Escala (getint "Valor da Escala do projeto: " ) )
  (setq Delta (/ (* 0.3 Escala ) 1000))
  (princ "\nRéguas: <40>;<50>;<60>;<80>;<100>;<120>;<140>;<175>;<200>;<240>;<290>;<350>;<425>;<450>")
  (initget 7)
  (setq regua (getint "\nForneça a régua do desenho: "))
  (command "_.STYLE" "ROMANS" "ROMANS" "0" "1.0" "0" "" "" "")
  (cond
     	((= regua 40) (setq Ht 1.0))
     	((= regua 50) (setq Ht 1.3))
     	((= regua 60) (setq Ht 1.6))
     	((= regua 80) (setq Ht 2.0))
   	((= regua 100) (setq Ht 2.5))
        ((= regua 120) (setq Ht 3.0))
        ((= regua 140) (setq Ht 3.5))
        ((= regua 175) (setq Ht 4.0))
        ((= regua 200) (setq Ht 4.5))
        ((= regua 240) (setq Ht 6.0))
        ((= regua 290) (setq Ht 7.5))
        ((= regua 350) (setq Ht 9.0))
        ((= regua 425) (setq Ht 11.0))
        ((= regua 450) (setq Ht 13.0))
        (T otherwise (setq Ht 1.0))
  )
  (setq Ht (* Ht (/ Escala 1000.0)))
  (setvar "TEXTSIZE" Ht)
  (setq i (getint "Número inicial: "))
  (setvar "osmode" 1)
  (while (setq Pto_bloco (Getpoint "Selecione o Ponto: " )) ;; primeiro while 
	        (command "_.layer" "m" "TXT_ESTACA" "")
                (command "_.text" "J" "TC" Pto_bloco Ht "0.0" (itoa i))
                (setvar "osmode" 0)
                (setq i (1+ i))
                (setvar "osmode" 1)
   ) ;;fim do primeiro if
   (setvar "cmdecho" olcmdecho)
   (setvar "osmode" oldosmode)
   (command "_.-Layer" "m" oldlayer "")
   (princ)
)
(princ "\nDigite 'NESTACA' para iniciar")
