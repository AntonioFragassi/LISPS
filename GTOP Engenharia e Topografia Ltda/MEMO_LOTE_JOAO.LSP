;; Gera Memorial de um lote regular urbano de até 6 vertices. O lote pode apresentar até dois chanfros.
;;(command "_.insert" "LOTE.dwg" PTOMED "1" "" "0" QUADRA LOTE textpontos Frente LatEsq Fundo LatDir (tiraponto AREALOTE) (tiraponto PERIM))

(defun LIMITE (  / lista NOMEATRIB)
  	(setq OBJETO (ssget "_all" '((0 . "INSERT") (2 . "BBL_IMIGRANTES"))))
  	(if (= (sslength OBJETO) 1)
    	    (progn
  		(setq OBJETO (ssname OBJETO 0))
  		(while (/= (cdr (assoc 0 (entget OBJETO))) "SEQEND")
        		(setq OBJETO (entnext OBJETO))
  			(setq lista (entget OBJETO))
        		(setq NOMEATRIB (cdr (assoc 2 lista)))
        		(cond
	  			((= NOMEATRIB "LSE" ) (setq LSE (cdr (assoc 10 lista))) )
          			((= NOMEATRIB "LID" ) (setq LID (cdr (assoc 10 lista))) )
	 		)
    		)
	    	(setq PTQD (list (car LSE) (cadr LID) 0.0))
	    );;FIM DO PROGN
       )
)



(defun malha ( / Comp_Conj oldangbase oldangdir oldosmode pt1 pt2 xpt1 xpt2 ypt1 ypt2 xmax xmin passo primx primy deltax deltay quantx quanty escolha ptext op
		   pbase afast northin eastin)
	(setq oldangbase (getvar "angbase"))
	(setvar "angbase" 0)
	(setq oldangdir (getvar "angdir"))
	(setvar "angdir" 1)
	(setq oldosmode (getvar "osmode"))
	(setvar "osmode" 0)
	(if (= ESCALA nil) (LEROY))
	(princ (strcat "\nEscala 1:" (rtos escala 2 0)))
	(LIMITE)
	(setq pt1 LSE)
	(setq pt2 LID)
	(setq xpt1 (car pt1))
	(setq xpt2 (car pt2))
	(setq ypt1 (cadr pt1))
	(setq ypt2 (cadr pt2))
	(if (> xpt1 xpt2) 	(progn
				(setq xmax xpt1) 
				(setq xmin xpt2) 
				)
				(progn
				(setq xmax xpt2) 
				(setq xmin xpt1) 
				)
	)
	(if (> ypt1 ypt2) 	(progn
				(setq ymax ypt1) 
				(setq ymin ypt2) 
				)
				(progn
				(setq ymax ypt2) 
				(setq ymin ypt1) 
				)
	)
	(setq passo (/ (* escala 1000) 10))
	(setq primx (* (1+ (fix (/ xmin passo))) passo)) 
	(setq primy (* (1+ (fix (/ ymin passo))) passo))
	(setq deltax (- xmax primx))
	(setq deltay (- ymax primy))
	(setq quantx (1+ (fix (/ deltax passo))))
	(setq quanty (1+ (fix (/ deltay passo))))
	(setq escolha 2)
	(setq pbase (list xmax ymin))
        (setq deltax (* -1 deltax))
	(setq afast (* 0.0017098 (* 1000 escala)))
	(repeat quanty
		(command "_.layer" "m" "MALHA_UTM" "")
		(command "_.line" (list xmin primy) (list xmax primy) "")
		;(setq northin (strcat "N=" (rtos primy 2 0)))
        	(setq northin (rtos primy 2 0))
		(command "_.layer" "m" "TXT_MALHA_UTM" "")
		(setq ptext (list xmax primy))
		(setq ptext (cal "ptext+[afast,0]"))
		(command "_.text" "j" "ml" ptext "" "0" northin)
		(setq primy (+ primy passo))
	)
	(repeat quantx
		(command "_.layer" "m" "MALHA_UTM" "")
		(command "_.line" (list primx ymin) (list primx ymax) "")
		;(setq eastin (strcat "E=" (rtos primx 2 0)))
        	(setq eastin (rtos primx 2 0))
		(command "_.layer" "m" "TXT_MALHA_UTM" "")
		(setq ptext (list primx ymin))
		(setq ptext (cal "ptext-[0,afast]"))
		(command "_.text" "j" "tc" ptext "" "0" eastin)
		(setq primx (+ primx passo))
	)
	(setvar "angbase" oldangbase)
	(setvar "angdir" oldangdir)
	(setvar "osmode" oldosmode)
	
)


(defun LEROY (/ regua fator h)
 (prompt "\nAJUSTA AS LETRAS COM O PADRAO LEROY")
 (initget 1  "40 50 60 80 100 120 140 175 200")
 (setq regua (getint "\nTamanho da Regua (40 50 60 80 100 120 140 175 200): ")
       ESCALA (getreal "Escala do desenho: ")
 )
 (cond ((= regua  40) (setq h 1.0))
       ((= regua  50) (setq h 1.3))
       ((= regua  60) (setq h 1.6))
       ((= regua  80) (setq h 2.0))
       ((= regua 100) (setq h 2.5))
       ((= regua 120) (setq h 3.0))
       ((= regua 140) (setq h 3.5))
       ((= regua 175) (setq h 4.0))
       ((= regua 200) (setq h 4.5))
 )
 (setq ESCALA (/ ESCALA 1000.0))
 (if (< regua 201)
   (setvar "textsize" (* h ESCALA))
   (setvar "textsize" 1.6)
  )
)


(defun BOTABBL ( / LOCAL VALCF1 VLACF2 VALESC) ;;DISTFRE DISTLE DISTFUN DISTLD CHANF1 CHANF2
        (command "_.layer" "m" "CARIMBO" "")
        (if (= CHANF1 nil ) (setq VALCF1 "-") (setq  VALCF1 (strcat (tiraponto CHANF1) "m")))
        (if (= CHANF2 nil ) (setq VALCF2 "-") (setq  VALCF2 (strcat (tiraponto CHANF2) "m")))
        (setq VALESC (strcat "1:" (rtos ( * 1000 ESCALA) 2 0)))
        (setq LOCAL (strcat "LOTE " LOTE " - QUADRA " QUADRA " - CHÁCARA JARUMÃ - NOVO GAMA/GO") )       
	(command "_.insert" "T:\\Biblioteca CAD\\Blocos\\TOPOGRAFIA\\BBL_JOAO.dwg" PTOMED ESCALA "" "0" (strcat "Kr=" (tiraponto (rtos KR 2 7))) LOCAL (tiraponto AREALOTE) (strcat (tiraponto PERIM) "m")
		 (strcat (tiraponto DISTFRE) "m") (strcat (tiraponto DISTFUN) "m") (strcat (tiraponto DISTLD) "m") (strcat (tiraponto DISTLE) "m")
		 VALCF1 VALCF2 VALESC "" "" DATA)
        (command "_.layer" "m" "TXT_LOTE_TOPOGRAFICO" "")
        (command "_.insert" "T:\\Biblioteca CAD\\Blocos\\TOPOGRAFIA\\NOME_LOTE.dwg" PTOMED ESCALA "" "0" LOTE (strcat "Área = " (tiraponto AREALOTE)))
)

	

(defun OCTANTE ( ANG / RESP )
    (cond
	((and (>= ANG 0.0)(< ANG 90.0)) (setq RESP ANG))
        ((and (>= ANG 90.0)(< ANG 180.0)) (setq RESP (- ANG 180.0)))
	((and (>= ANG 180.0)(< ANG 270.0)) (setq RESP (- ANG 180.0)))
	((and (>= ANG 270.0)(<= ANG 360.0)) (setq RESP (- ANG 360.0)))
    )
  (setq RESP RESP)
 )

(defun QUADRO_AZIMUTE ( / PT1 j XX YY DESCPT1 DESCPT2)
        (command "_.layer" "m" "QUADRO_AZIMUTE_DISTANCIA" "")
	;;(setq PT1 PTQD)
        (setq PT1 (getpoint "\nClique no ponto de Insercao do quadro." ))
        (command "_.insert" "T:\\Biblioteca CAD\\Blocos\\TOPOGRAFIA\\cabecalho_QUADRO.dwg" PT1 ESCALA "" "0")
        (setq PASSO (* (* ESCALA 16.5) 1.0))
        (setq PASSO (list 0.0 PASSO 0.0))
        (setq PT1  (c:cal "PT1 - PASSO") )
	(setq j 0)
        (setq PASSO (* (* ESCALA 3.2) 1.0))
        (setq PASSO (list 0.0 PASSO 0.0))
	(while (< j (1- (length DADOS_LINHA)))
	      (progn
  			(setq XX (car (last (assoc 2 (nth j DADOS_LINHA))))) (setq YY (cadr (last (assoc 2 (nth j DADOS_LINHA)))))
		        (setq DESCPT1 (cdr (assoc 1 (nth j DADOS_LINHA))))
		        (setq DESCPT2 (cdr (assoc 1 (nth (1+ j) DADOS_LINHA))))
		        (setq AZ (cdr (assoc 4 (nth j DADOS_LINHA)))) (setq DIST (cdr (assoc 3 (nth j DADOS_LINHA))))
		        (command "_.insert" "T:\\Biblioteca CAD\\Blocos\\TOPOGRAFIA\\linha_QUADRO.dwg" PT1 ESCALA "" "0" DESCPT1 DESCPT2 (substr AZ 4) (TIRAPONTO DIST) (FORMATEQ XX) (FORMATNQ YY))
		        (setq PT1  (c:cal "PT1 - PASSO") )
			(setq j (1+ j))
	       )
	  )
        (setq j (1- (length DADOS_LINHA)))
  	(setq XX (car (last (assoc 2 (nth j DADOS_LINHA))))) (setq YY (cadr (last (assoc 2 (nth j DADOS_LINHA)))))
	(setq DESCPT1 (cdr (assoc 1 (nth j DADOS_LINHA))))
	(setq DESCPT2 (cdr (assoc 1 (nth 0 DADOS_LINHA))))
	(setq AZ (cdr (assoc 4 (nth j DADOS_LINHA)))) (setq DIST (cdr (assoc 3 (nth j DADOS_LINHA))))
	(command "_.insert" "T:\\Biblioteca CAD\\Blocos\\TOPOGRAFIA\\linha_QUADRO.dwg" PT1 ESCALA "" "0" DESCPT1 DESCPT2 (substr AZ 4) (TIRAPONTO DIST) (FORMATEQ XX) (FORMATNQ YY))
)

(defun BOTAZDIST ( / ANG PM PT1 PT2 PM TEXTO1 j)
        (command "_.layer" "m" "TXT_AZIMUTE_DISTANCIA" "")
	(setq j 0)
	(while (< j (1- (length DADOS_LINHA)))
	      (progn
		        (setq PT1 (cadr (assoc 2 (nth j DADOS_LINHA))))
		        (setq PT2 (cadr (assoc 2 (nth (1+ j) DADOS_LINHA))))
		        (setq AZ (cdr (assoc 4 (nth j DADOS_LINHA)))) (setq DIST (cdr (assoc 3 (nth j DADOS_LINHA))))
		        (setq ANG (atof (angtos (angle PT1 PT2)0 12)))
		        (setq ANG (OCTANTE ANG))
		        (setq PM  (c:cal "(PT1 + PT2) / 2") )
		        (command "_.insert" "T:\\Biblioteca CAD\\Blocos\\TOPOGRAFIA\\AZDIST.dwg" PM ESCALA "" ANG (strcat (TIRAPONTO DIST)"m") AZ )
			(setq j (1+ j))
	       )
	  )
        (setq j (1- (length DADOS_LINHA)))
	(setq PT1 (cadr (assoc 2 (nth j DADOS_LINHA))))
	(setq PT2 (cadr (assoc 2 (nth 0 DADOS_LINHA))))
	(setq AZ (cdr (assoc 4 (nth j DADOS_LINHA)))) (setq DIST (cdr (assoc 3 (nth j DADOS_LINHA))))
  	(setq ANG (atof (angtos (angle PT1 PT2)0 12)))
	(setq ANG (OCTANTE ANG))
	(setq PM  (c:cal "(PT1 + PT2) / 2") )
	(command "_.insert" "T:\\Biblioteca CAD\\Blocos\\TOPOGRAFIA\\AZDIST.dwg" PM ESCALA "" ANG (strcat (TIRAPONTO DIST)"m") AZ )
)


(defun IMPRESSAO ( / f pref nomef lnome nomef nomef)
		(setq pref (getvar "dwgprefix"))
		(setq nomef (getvar "dwgname"))
		(setq lnomef (strlen nomef))
		(setq nomef (substr nomef 1 (- lnomef 3)))
		(setq nomef (strcat pref "MEMORIAL_QD_" QUADRA "_LT_" LOTE ".doc"))
		(setq f (open nomef "w" ))
		(write-line "MEMORIAL DESCRITIVO" f)
		(write-line "" f)
		(write-line "" f)
		(write-line (strcat "IMÓVEL: Lote " LOTE ) f)
		(write-line (strcat "ENDEREÇO: QUADRA " QUADRA) f), CHÁCARA JARUMÃ
		(write-line (strcat "ESTADO: GO                   MUNICÍPIO: NOVO GAMA/GO") f)
		(write-line "" f)
		(write-line "" f)
		(write-line TEXTOMEMO f)
  		(write-line "" f)
		(write-line "" f)
                (write-line "Planaltina de Goiás, 14 de Dezembro de 2012" f)
    		(write-line "" f)
		(write-line "" f)
  		(write-line "____________________________________________________________" f)
                (write-line "Antônio de Pádua Mendonça Fragassi" f)
                (write-line "Engenheiro Agrimensor - CREA: DF-10.446/D" f)         
		(close f)
		(princ)
		(princ (strcat "\n----->Informações escritas no arquivo " nomef))
		(princ)
 )

(defun c:KR()
    (princ "\nAtualizacao do KR.")
    (capaerre)
    (princ (strcat "\nEntre com KR <" (rtos KR 2 7) "> : "))
    (setq temp KR)
    (setq KR (getreal))
    (if (= KR nil) (setq KR temp))
    (SETVAR "USERR1" KR)
    (princ (strcat "\nKR atual ==> " (rtos KR 2 7)))
    (princ)
)
(defun capaerre( / temp)
    (if (< (GETVAR "USERR1") 1.0)
      (progn
	(setq KR 1.0000000)
	(princ "\nKR nao cadastrado!!!")
	(princ (strcat "\nEntre com KR <" (rtos KR 2 7) "> : "))
	(setq temp KR)
	(setq KR (getreal))
	(if (= KR nil) (setq KR temp))
	(princ (strcat "\nKR atual ==> " (rtos KR 2 7)))
	(SETVAR "USERR1" KR)
      )
    )

    (if (not KR)
      (progn
	(setq KR (GETVAR "USERR1"))
	(setq hakr 1)
      )
    )

    (princ (strcat "\nKR atual ==> " (rtos KR 2 7)))
    (princ)
)

(defun CALCAREA ( / TAM ZZZ N1 PT1 PT2 PT3 PT4)
   	(setq TAM (length DADOS_LINHA))
  	(cond
		((= TAM 4) (command "_.area" (last (assoc 2 (nth 0 DADOS_LINHA)))
				             (last (assoc 2 (nth 1 DADOS_LINHA)))
				             (last (assoc 2 (nth 2 DADOS_LINHA)))
				             (last (assoc 2 (nth 3 DADOS_LINHA))) ""
		))
		((= TAM 5) (command "_.area" (last (assoc 2 (nth 0 DADOS_LINHA)))
				             (last (assoc 2 (nth 1 DADOS_LINHA)))
				             (last (assoc 2 (nth 2 DADOS_LINHA)))
				    	     (last (assoc 2 (nth 3 DADOS_LINHA)))
				             (last (assoc 2 (nth 4 DADOS_LINHA))) ""
		))
		((= TAM 6) (command "_.area" (last (assoc 2 (nth 0 DADOS_LINHA)))
				             (last (assoc 2 (nth 1 DADOS_LINHA)))
				             (last (assoc 2 (nth 2 DADOS_LINHA)))
				    	     (last (assoc 2 (nth 3 DADOS_LINHA)))
				    	     (last (assoc 2 (nth 4 DADOS_LINHA)))				    
				             (last (assoc 2 (nth 5 DADOS_LINHA))) ""
		))
	)
    	(setq ZZZ(getvar 'area))
    	(setq ZZZ (/ ZZZ (* KR KR)))
    	(setq ZZZ (strcat (rtos ZZZ 2 2) "m²"))
    	(setq AREALOTE ZZZ)
)

(defun C:AREALOTE ( / ZZZ PTOMED AREALOTE LOTE)
        (LEROY)
        (setq LISTA_PONTOS '())
        (while T
	  	(progn
		        (setvar "osmode" 1)
		        (setq LISTA_PONTOS '())
		        (while (setq PTOMED (getpoint "\nPróximo Ponto." ))
		        	(setq LISTA_PONTOS (append LISTA_PONTOS (list PTOMED) ))
			)
		        (setvar "osmode" 0)
		        (setq TAM (length LISTA_PONTOS))
		    	(cond
				((= TAM 4) (command "_.area"
						(nth 0 LISTA_PONTOS)
				             	(nth 1 LISTA_PONTOS)
				             	(nth 2 LISTA_PONTOS)
				             	(nth 3 LISTA_PONTOS) ""
				))
				((= TAM 5) (command "_.area"
						(nth 0 LISTA_PONTOS)
				             	(nth 1 LISTA_PONTOS)
				             	(nth 2 LISTA_PONTOS)
						(nth 3 LISTA_PONTOS)
				             	(nth 4 LISTA_PONTOS) ""
				))
				((= TAM 6) (command "_.area"
						(nth 0 LISTA_PONTOS)
				             	(nth 1 LISTA_PONTOS)
				             	(nth 2 LISTA_PONTOS)
						(nth 3 LISTA_PONTOS)
						(nth 4 LISTA_PONTOS)    
				             	(nth 5 LISTA_PONTOS) ""
				))
				((= TAM 7) (command "_.area"
						(nth 0 LISTA_PONTOS)
				             	(nth 1 LISTA_PONTOS)
				             	(nth 2 LISTA_PONTOS)
						(nth 3 LISTA_PONTOS)
						(nth 4 LISTA_PONTOS)
						(nth 5 LISTA_PONTOS)    
				             	(nth 6 LISTA_PONTOS) ""
				))
				((= TAM 8) (command "_.area"
						(nth 0 LISTA_PONTOS)
				             	(nth 1 LISTA_PONTOS)
				             	(nth 2 LISTA_PONTOS)
						(nth 3 LISTA_PONTOS)
						(nth 4 LISTA_PONTOS)
						(nth 5 LISTA_PONTOS)
						(nth 6 LISTA_PONTOS)     
				             	(nth 7 LISTA_PONTOS) ""
				))
			)
    			(setq ZZZ(getvar 'area))
    			(setq ZZZ (/ ZZZ (* KR KR)))
    			(setq ZZZ (strcat (rtos ZZZ 2 2) "m²"))
    			(setq AREALOTE ZZZ)
        		(setq LOTE (getstring "\nFonerça o número do lote: "))
        		(setvar "osmode" 4)
        		(setq PTOMED (getpoint "\nClique no ponto de Inserção do bloco." ))
        		(setvar "osmode" 0)
        		(command "_.layer" "m" "TXT_LOTE_TOPOGRAFICO" "")
        		(command "_.insert" "T:\\Biblioteca CAD\\Blocos\\TOPOGRAFIA\\NOME_LOTE.dwg" PTOMED ESCALA "" "0" LOTE (tiraponto AREALOTE))
		  )
	  )
)

(defun CONFRONTANTE ( TEXTO / COMP)
  (if (/= TEXTO nil)
  	(progn
           	(setq COMP (strlen TEXTO))
		(if (<= COMP 2) (setq TEXTO (strcat "LOTE " TEXTO ) ))
	  )
         (setq TEXTO "Verificar Confrontante")
  )
  (setq TEXTO TEXTO)
)

(defun tiraponto (TEXTO / AUX j txt )
  	(setq comp (strlen TEXTO))
        (setq i 0)
        (setq aux "")
        (repeat (strlen TEXTO)
	  	(setq txt (substr TEXTO (setq i(1+ i)) 1))
	        (cond
		  ((= txt ".") (setq AUX (strcat aux "," )))
	          ((/= txt ",") (setq AUX (strcat aux txt )))
		 )
	)
  	(setq aux aux)
 )

(defun FORMATE ( XX / E1)
    (setq E1 (rtos XX 2 3)) 
    (setq E1 (strcat (substr E1 1 3) "." (substr E1 4 3) "," (substr E1 8 3) ))
    (setq E1 (strcat "E="  E1))
    (setq XX E1)
)

(defun FORMATN ( YY / N1)
    (setq N1 (rtos YY 2 3))
    (setq N1 (strcat (substr N1 1 1) "." (substr N1 2 3) "." (substr N1 5 3) "," (substr N1 9) ))
    (setq N1 (strcat "N="  N1))
    (setq YY N1)
)

(defun FORMATEQ ( XX / E1)
    (setq E1 (rtos XX 2 3)) 
    (setq E1 (strcat (substr E1 1 3) "." (substr E1 4 3) "," (substr E1 8 3) ))
    (setq XX E1)
)

(defun FORMATNQ ( YY / N1)
    (setq N1 (rtos YY 2 3))
    (setq N1 (strcat (substr N1 1 1) "." (substr N1 2 3) "." (substr N1 5 3) "," (substr N1 9) ))
    (setq YY N1)
)

(defun AZ_DIST (PONTOS / P1 P2 dkr D1 AUX QD DX DY GRAU MINUTO SEGUNDO TEMP)
        (setq aux 0.0 grau 0.0 minuto 0.0 sengundo 0.0 temp 0.0)
        (setq P1 (car PONTOS))
        (setq P2 (last PONTOS))
   	(setq DX (- (car P2) (car P1)))
   	(setq DY (- (car (cdr P2)) (car (cdr P1))))
   	(if (= DX 0.0)( if (> DY 0.0) (setq AZ 0.0) (setq AZ 180.0)))
   	(if (= DY 0.0) ( if (> DX 0.0) (setq AZ 90.0) (setq AZ 270.0)))
   	(setq QD 0)
   	;;(princ 1)
   	(if (and (> DX 0.0) (> DY 0.0)) (setq QD 1))
   	(if (and (> DX 0.0) (< DY 0.0)) (setq QD 2))
   	(if (and (< DX 0.0) (< DY 0.0)) (setq QD 3))
   	(if (and (< DX 0.0) (> DY 0.0)) (setq QD 4))
   	(cond
     		((= QD 1) (setq aux (atan (abs (/ DX DY)))))
     		((= QD 2) (setq aux (- pi (atan (abs (/ DX DY))))))
     		((= QD 3) (setq aux (+ pi (atan (abs (/ DX DY))))))
     		((= QD 4) (setq aux (- (* 2 pi) (atan (abs (/ DX DY))))))
   	)
   	;;(princ 2)
   	(setq aux (* 180.0 (/ aux pi)))
   	(setq grau (fix aux))
   	(setq temp (* 60 (- aux grau)))
   	(setq minuto (fix temp))
   	(setq temp (* 60 (- temp minuto)))
   	;;(setq segundo (fix temp))
   	(setq segundo temp)
   	(setq grau (rtos grau 2 0))
   	(setq minuto (rtos minuto 2 0))
   	(setq segundo (rtos segundo 2 0))
   	(setq AZ (strcat "Az=" grau "°" minuto "'" segundo "\""))
   	(setq D1 (distance P1 P2))
        (capaerre)
   	(setq D1 (/ D1 KR))
   	(setq D1 (rtos D1 2 2))
   	(setq DIST D1)
   )

(defun GERAMEMO (/ j DIST DESCPT1 CONFRONTANTE TEXTO1 XX YY AUX1)
  	(setq TEXTO1 "" TEXTO2 ""  TEXTO3 "" TEXTO4 "")
     	(setq TAM (length DADOS_LINHA))
  	(setq XX (car (last (assoc 2 (nth 0 DADOS_LINHA))))) (setq YY (cadr (last (assoc 2 (nth 0 DADOS_LINHA)))))
        (setq DESCPT1 (cdr (assoc 1 (nth 0 DADOS_LINHA)))) (setq AZ (cdr (assoc 4 (nth 0 DADOS_LINHA)))) (setq DIST (cdr (assoc 3 (nth 0 DADOS_LINHA))))
        (setq TEXTO1 (strcat "Inicia a descrição desse perímetro no vértice " DESCPT1 " de coordenadas " (FORMATE XX) " e " (FORMATN YY)
 			 ", deste segue por linha seca com azimute plano de " AZ " e distância plana de " (tiraponto DIST) "m até atingir o vértice " ))
	(setq j 1)
	(while (<= j (1- (length DADOS_LINHA)))
	      (progn
  			(setq XX (car (last (assoc 2 (nth j DADOS_LINHA))))) (setq YY (cadr (last (assoc 2 (nth j DADOS_LINHA)))))
		        (setq DESCPT1 (cdr (assoc 1 (nth j DADOS_LINHA)))) (setq AZ (cdr (assoc 4 (nth j DADOS_LINHA)))) (setq DIST (cdr (assoc 3 (nth j DADOS_LINHA))))
			(setq CONFRONTANTE (cdr (assoc 5 (nth (1- j) DADOS_LINHA))))
	       		(setq TEXTO2 (strcat TEXTO2 DESCPT1 ", de coordenadas " (FORMATE XX) " e " (FORMATN YY) ", confrontando nesse trecho com " CONFRONTANTE
  			 "; deste segue por linha seca com azimute plano de " AZ " e distância plana de " (tiraponto DIST) "m até atingir o vértice " ))
			(setq j (1+ j))
	       )
	  )
        (setq CONFRONTANTE (cdr (assoc 5 (nth (1- j) DADOS_LINHA))))
	(setq DESCPT1 (cdr (assoc 1 (nth 0 DADOS_LINHA))))
    	(setq TEXTO3 (strcat DESCPT1 ", ponto inicial da descrição desse perímetro, confrontando nesse trecho com " CONFRONTANTE
	", encerrando assim a descrição desse memorial descritivo. Todas as coordenadas aqui descritas estão georreferenciadas ao Sistema Geodésico Brasileiro e encontram-se representadas no sistema UTM, referenciadas ao Meridiano Central -45° WGr, tendo como DATUM o SIRGAS2000. Os azimutes foram calculados no plano de projeção UTM e as distâncias foram reduzidas ao plano topográfico utilizado o Kr=" (rtos KR 2 7)
	" como fator de correção."))
	(setq TAM (length DADOS_LINHA))
	(cond
	  	((= TAM 4)
  			(progn
			  	(setq DISTFRE (cdr (assoc 3 (nth 0 DADOS_LINHA))))
			  	(setq DISTLE (cdr (assoc 3 (nth 1 DADOS_LINHA))))
			  	(setq DISTFUN (cdr (assoc 3 (nth 2 DADOS_LINHA))))
			  	(setq DISTLD (cdr (assoc 3 (nth 3 DADOS_LINHA))))
			  	(setq TEXTO4 (strcat "O presente memorial corresponde ao lote urbano denominado de Lote " LOTE " com as seguintes características: " (tiraponto DISTFRE) "m de frente, "
		    		(tiraponto DISTFUN) "m de fundo, " (tiraponto DISTLE) "m de lado esquerdo e " (tiraponto DISTLD) "m de lado direito, com área total de " (tiraponto AREALOTE) " e perímetro de " (tiraponto PERIM) "m. " ))
			 )
		 )
	  	((= TAM 5)
  			(progn
			  	(setq DISTFRE (cdr (assoc 3 (nth 0 DADOS_LINHA))))
			        	(setq CHANF1 (cdr (assoc 3 (nth 1 DADOS_LINHA))))
			  	(setq DISTLE (cdr (assoc 3 (nth 2 DADOS_LINHA))))
			  	(setq DISTFUN (cdr (assoc 3 (nth 3 DADOS_LINHA))))
			  	(setq DISTLD (cdr (assoc 3 (nth 4 DADOS_LINHA))))
			        	(if (< (distof DISTFRE) 5.00)
				    (progn
				     	(setq AUX1 DISTFRE)
				      	(setq DISTFRE CHANF1)
				      	(setq CHANF1 AUX1)
				     )
				)
			  	(setq TEXTO4 (strcat "O presente memorial corresponde ao lote urbano denominado de Lote " LOTE " com as seguintes características: " (tiraponto DISTFRE) "m de frente, "
		    		(tiraponto DISTFUN) "m de fundo, " (tiraponto DISTLE) "m de lado esquerdo, " (tiraponto DISTLD) "m de lado direito e " (tiraponto CHANF1) "m de chanfro, com área total de " (tiraponto AREALOTE) " e perímetro de " (tiraponto PERIM) "m. " ))
			 )
		 )
	  	((= TAM 6)
  			(progn
			  	(setq CHANF1 (cdr (assoc 3 (nth 0 DADOS_LINHA))))
			        (setq DISTFRE (cdr (assoc 3 (nth 1 DADOS_LINHA))))
			  	(setq CHANF2 (cdr (assoc 3 (nth 2 DADOS_LINHA))))
			  	(setq DISTLE (cdr (assoc 3 (nth 3 DADOS_LINHA))))
			  	(setq DISTFUN (cdr (assoc 3 (nth 4 DADOS_LINHA))))
			  	(setq DISTLD (cdr (assoc 3 (nth 5 DADOS_LINHA))))
			  	(setq TEXTO4 (strcat "O presente memorial corresponde ao lote urbano denominado de Lote " LOTE " com as seguintes características: " (tiraponto DISTFRE) "m de frente, "
		    		(tiraponto DISTFUN) "m de fundo, " (tiraponto DISTLE) "m de lado esquerdo, " (tiraponto DISTLD) "m de lado direito, " (tiraponto CHANF1) "m de chanfro a direita, " (tiraponto CHANF2) "m de chanfro a esquerda, com área total de " (tiraponto AREALOTE) " e perímetro de " (tiraponto PERIM) "m. " ))
			 )
		 )
		
		
	)
  	(setq TEXTOMEMO (strcat TEXTO4 TEXTO1 TEXTO2 TEXTO3))
)

(defun DADOS_PONTO ( / PONTOS ASSOC1 ASSOC2 ASSOC3 ASSOC4 ASSOC5 P1 TAM CONF TIPOLT)
	    (setq MSN1 "Selecione os pontos do lote na sequencia FRENTE > LADO ESQUERDO > FUNDO > LADO DIREITO :")
            (princ MSN1)
	    (setq LISTOBJETOS (ssget '((0 . "INSERT") (2 . "SIMB_PONTO1"))))
	    (setq CONF '())
            (setq DADOS_LINHA '())
            ;;(setq Comp_Conj (sslength LISTOBJETO))
	    (if (>= (sslength LISTOBJETOS) 3);; IF 1
	        (progn
		      	(setq Comp_Conj 0)
		        (setq ASSOC3 (cons 3 "") ASSOC4 (cons 4 "") ASSOC5 (cons 5 ""))
		         ;(print "*************** 1 *************")
                      	(while (< Comp_Conj (sslength LISTOBJETOS)) ;; WHILE 2
			   (progn
	      			(setq OBJETO (ssname LISTOBJETOS Comp_Conj))
			        (setq lista (entget OBJETO))
				(setq pto (cdr (assoc 10 lista)))
			        (setq ASSOC2 (cons 2 (list pto)))
			        (setq OBJETO (entnext OBJETO))
			        (setq lista (entget OBJETO))
				(setq desc_pto (cdr (assoc 1 lista)))
			        (setq ASSOC1 (cons 1 desc_pto))
				;;;(AZ_DIST PONTOS)
			        (setq DADOS_LINHA (append DADOS_LINHA (list (list ASSOC1 ASSOC2 ASSOC3 ASSOC4 ASSOC5))))
				(setq Comp_Conj (1+ Comp_Conj))
			    );; FIM DO PROGN
		      	);; FIM DO WHILE 2
		        (setq i 0)
		        (while (< i (1- (length DADOS_LINHA)))
			  (progn
			        (setq PONTOS '())
				(setq PONTOS (list (last (assoc 2 (nth i DADOS_LINHA))) (last (assoc 2 (nth (1+ i) DADOS_LINHA)))))
			        (setq listaux (nth i DADOS_LINHA))
			        ;;(subst 'qq 'b sample)
				(AZ_DIST PONTOS)
			        (setq ASSOC3 (cons 3 DIST) ASSOC4 (cons 4 AZ))
			        (setq listaux (subst ASSOC3 (assoc 3 listaux) listaux))
			        (setq listaux (subst ASSOC4 (assoc 4 listaux) listaux))
			        (setq DADOS_LINHA (subst listaux (nth i DADOS_LINHA) DADOS_LINHA))
			        (setq i (1+ i))
			    )
			)
		        (setq i (1-(length DADOS_LINHA)))
		        (setq PONTOS (list (last (assoc 2 (nth i DADOS_LINHA))) (last (assoc 2 (nth 0 DADOS_LINHA)))))
			(setq listaux (nth i DADOS_LINHA))
		        (AZ_DIST PONTOS)
			(setq ASSOC3 (cons 3 DIST) ASSOC4 (cons 4 AZ))
			(setq listaux (subst ASSOC3 (assoc 3 listaux) listaux))
			(setq listaux (subst ASSOC4 (assoc 4 listaux) listaux))
			(setq DADOS_LINHA (subst listaux (nth i DADOS_LINHA) DADOS_LINHA))
                        (setq PTOMED '(0.0 0.0 0.0) P1 '(0.0 0.0 0.0) PERIM 0.0 )
		        (setq i 0)
		        (while (< i  (length DADOS_LINHA))
			  	(progn
				        (setq p1 (last (assoc 2 (nth i DADOS_LINHA))))
					(setq PTOMED (c:cal "PTOMED + P1"))
				        (setq PERIM (+ PERIM  (distof (cdr (assoc 3 (nth i DADOS_LINHA)))) ))
				        (setq i (1+ i))
				)
			)
		        (setq PERIM (rtos PERIM 2 2))
		        (setq TAM (length DADOS_LINHA))
		        (setq PTOMED  (c:cal "PTOMED / TAM") )
		        (setq texto (cdr (assoc 1 (entget (car (entsel "Selecione Frente: " ))))))
		        (setq Frente (confrontante texto))
		        (setq texto (cdr (assoc 1 (entget (car (entsel "Selecione Lateral Esquerda: " ))))))
		        (setq LatEsq (confrontante texto))
		        (setq texto (cdr (assoc 1 (entget (car (entsel "Selecione Fundo: " ))))))
		        (setq Fundo (confrontante texto))
		        (setq texto (cdr (assoc 1 (entget (car (entsel "Selecione Lateral Direita: " ))))))
		        (setq LatDir (confrontante texto))
	    		(cond
	      			((= (length DADOS_LINHA) 4) (setq CONF (list Frente LatEsq Fundo LatDir)))
	      			((= (length DADOS_LINHA) 5) (setq CONF (list Frente Frente LatEsq Fundo LatDir)))
	      			((= (length DADOS_LINHA) 6) (setq CONF (list Frente Frente Frente LatEsq Fundo LatDir)))
	     		)
		        (setq i 0)
		        (while (<= i (1- (length DADOS_LINHA)))
			   		(progn
						(setq ASSOC5 (cons 5 (nth i CONF)))
						(setq listaux (nth i DADOS_LINHA))
					  	(setq listaux (subst ASSOC5 (assoc 5 listaux) listaux))
			        		(setq DADOS_LINHA (subst listaux (nth i DADOS_LINHA) DADOS_LINHA))
					        (setq i (1+ i))
					 )
			 )
		         (CALCAREA)
		);; FIM DO PROGN DO THEN IF 1
	        (princ "Número de Vértices é memor do que 3. Refaça a seleção de pontos. " );; FIM DO ELSE IF 1
	)
  )
  
(defun c:memo_lote ( /  PTQD DATA DADOS_LINHA PERIM AREALOTE PTOMED ESCALA QDAZDIST DISTFRE DISTLE DISTFUN DISTLD CHANF1 CHANF2 LSE LID)
      	(setq oldangbase (getvar "angbase"));;correção 2
    	(setvar "angbase" 0.0)
    	(setq oldangdir (getvar "angdir"));;correção 2
    	(setvar "angdir" 0)
    	(setq oldosmode (getvar "osmode"))
    	(setvar "osmode" 0)
    	(setq oldcmdecho (getvar "cmdecho"))
    	(setvar "cmdecho" 0)
	(setq DATA "14/12/2012")
        (LEROY)
	(initget 1 "Sim Não")
        (setq QDAZDIST (getkword "\nInserir quadro de Azimute e Distância (S/N): "))
        (setq QUADRA (getstring "\nFonerça o número da Quadra: "))
        (setq QUADRA (strcase QUADRA))
        ;;(command "_.layer" "m" "PONTO_LOTE" "")
        (while T ;; WHILE 1
	    (setq DADOS_LINHA '() DISTFRE nil DISTLE nil DISTFUN nil DISTLD nil CHANF1 nil CHANF2 nil )
            (setq LOTE (getstring "\nFonerça o número do lote: "))
	    (DADOS_PONTO) (GERAMEMO) (IMPRESSAO) (BOTABBL)
	    (if (= QDAZDIST "Sim") (progn (QUADRO_AZIMUTE) (BOTAZDIST) ) )
	    (MALHA)
        );; FIM DO WHILE 1
	(setvar "cmdecho" olcmdecho)
	(princ)
)
(princ "\nDigite 'MEMO_LOTE' para iniciar - Digite AREALOTE para inserir area")
