(defun c:sb ()
	(setq oldosmode (getvar "osmode"))	
	(setvar "osmode" 3)
	;;;(setq blockname (strcase (getstring "\nEntre o nome do bloco: ")))
	(prompt "\nSelecione os blocos...")
	(setq blockset (ssget))
	(setq sclfctr (getreal "\nEntre fator de escala: ")) 
	;;;(setq crit (list (cons 0 "INSERT") (cons 2 blockname)))
	;;;(setq blockset (ssget "x" crit))
	(setq lentset (sslength blockset))
	(while (> lentset 0)
		(setq lentset (1- lentset))
		(setq temp (ssname blockset lentset))
		(setq entemp (entget temp))
		(setq pt (cdr (assoc 10 entemp)))
		(setq pt1 (cal "pt-[50,50]"))
		(setq pt2 (cal "pt+[50,50]"))
		(command "_.zoom" "W" pt1  pt2 "")
		(setq pt (GETPOINT "\nClique no ponto base:"))
		(command "_.Scale" temp "" pt sclfctr)
	)		
	(setvar "osmode" oldosmode)
)

(princ "\nDigite 'sb' para iniciar")
