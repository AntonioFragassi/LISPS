;; Coloca os blocos segundo a descrição 
(defun c:alarcao(/)
(princ "********* Espere um pouco - processando dados  ***********")
(setq olcmdecho (getvar "cmdecho"))
(setvar "cmdecho" 0)
(command "_.insert" "SIMB_CIRCULO" "196480.5328,8265975.7481" "0.1" "" "0" "1000" "CCC" "1078.8926")
(command "_.insert" "SIMB_CIRCULO" "196474.8161,8265960.0251,1079.5864" "0.1" "" "0" "1001" "CCC" "1079.5864")
(command "_.insert" "SIMB_CIRCULO" "196486.8652,8265990.1599,1078.1079" "0.1" "" "0" "1002" "CCC" "1078.1079")
(command "_.insert" "SIMB_CIRCULO" "196498.4292,8266019.0829,1076.5346" "0.1" "" "0" "1003" "CCC" "1076.5346")
(command "_.insert" "SIMB_CIRCULO" "196492.1851,8266004.9139,1077.2753" "0.1" "" "0" "1004" "CCC" "1077.2753")
(command "_.insert" "SIMB_CIRCULO" "196458.3501,8265963.0766,1079.9852" "0.1" "" "0" "1005" "CCC" "1079.9852")
(command "_.insert" "SIMB_CIRCULO" "196477.4267,8266017.2375,1077.2893" "0.1" "" "0" "1006" "CCC" "1077.2893")
(command "_.insert" "SIMB_CIRCULO" "196483.4159,8266030.3348,1076.5372" "0.1" "" "0" "1007" "CCC" "1076.5372")
(command "_.insert" "SIMB_CIRCULO" "196475.7691,8266003.8966,1077.75" "0.1" "" "0" "1008" "CCC" "1077.75")
(command "_.insert" "SIMB_CIRCULO" "196463.8759,8265972.4688,1079.4864" "0.1" "" "0" "1009" "CCC" "1079.4864")
(command "_.insert" "SIMB_CIRCULO" "196469.4012,8265989.674,1078.4855" "0.1" "" "0" "1010" "CCC" "1078.4855")
(command "_.insert" "SIMB_CIRCULO" "196505.4918,8266034.57,1075.6683" "0.1" "" "0" "1011" "CCC" "1075.6683")
(command "_.insert" "SIMB_CIRCULO" "196524.4802,8266041.7347,1074.8545" "0.1" "" "0" "1012" "CCC" "1074.8545")
(command "_.insert" "SIMB_CIRCULO" "196529.9012,8266055.0605,1074.1606" "0.1" "" "0" "1013" "CCC" "1074.1606")
(command "_.insert" "SIMB_CIRCULO" "196519.619,8266027.6223,1075.5799" "0.1" "" "0" "1014" "CCC" "1075.5799")
(command "_.insert" "SIMB_CIRCULO" "196505.5778,8265999.083,1077.4048" "0.1" "" "0" "1015" "CCC" "1077.4048")
(command "_.insert" "SIMB_CIRCULO" "196513.8328,8266011.2711,1076.3339" "0.1" "" "0" "1016" "CCC" "1076.3339")
(command "_.insert" "SIMB_CIRCULO" "196535.7714,8266067.1569,1073.1505" "0.1" "" "0" "1017" "CCC" "1073.1505")
(command "_.insert" "SIMB_CIRCULO" "196517.8813,8266064.1189,1073.8054" "0.1" "" "0" "1018" "CCC" "1073.8054")
(command "_.insert" "SIMB_CIRCULO" "196511.6442,8266050.7395,1074.6432" "0.1" "" "0" "1019" "CCC" "1074.6432")
(command "_.insert" "SIMB_CIRCULO" "196524.0339,8266081.393,1072.8419" "0.1" "" "0" "1020" "CCC" "1072.8419")
(command "_.insert" "SIMB_CIRCULO" "196542.8368,8266081.2097,1072.2233" "0.1" "" "0" "1021" "CCC" "1072.2233")
(command "_.insert" "SIMB_CIRCULO" "196532.1971,8266095.5971,1071.9052" "0.1" "" "0" "1022" "CCC" "1071.9052")
(command "_.insert" "SIMB_CIRCULO" "196443.0563,8265972.3526,1080.1095" "0.1" "" "0" "1023" "CCC" "1080.1095")
(command "_.insert" "SIMB_CIRCULO" "196528.6115,8265946.5441,1079" "0.1" "" "0" "1024" "CCC" "1079")
(command "_.insert" "SIMB_CIRCULO" "196446.8744,8265986.8658,1079.369" "0.1" "" "0" "1025" "CCC" "1079.369")
(command "_.insert" "SIMB_CIRCULO" "196456.7023,8266014.7408,1077.8447" "0.1" "" "0" "1026" "CCC" "1077.8447")
(command "_.insert" "SIMB_CIRCULO" "196453.5506,8266000.4019,1078.6207" "0.1" "" "0" "1027" "CCC" "1078.6207")
(command "_.insert" "SIMB_CIRCULO" "196898.3718,8266015.8227,1047.4908" "0.1" "" "0" "1028" "AUX1" "1047.4908")
(command "_.insert" "SIMB_CIRCULO" "196909.2459,8265972.8773,1047" "0.1" "" "0" "1029" "AUX2" "1047")
(command "_.insert" "SIMB_CIRCULO" "196904.5537,8265904.3288,1047.7362" "0.1" "" "0" "1030" "AUX1" "1047.7362")
(command "_.insert" "SIMB_CIRCULO" "196464.6893,8266025.8762,1077.0869" "0.1" "" "0" "1031" "CCC" "1077.0869")
(command "_.insert" "SIMB_CIRCULO" "196504.5123,8266080.2751,1073.3209" "0.1" "" "0" "1032" "CCC" "1073.3209")
(command "_.insert" "SIMB_CIRCULO" "196512.4319,8266093.524,1072.8229" "0.1" "" "0" "1033" "CCC" "1072.8229")
(command "_.insert" "SIMB_CIRCULO" "196498.6166,8266066.0705,1074.2644" "0.1" "" "0" "1034" "CCC" "1074.2644")
(command "_.insert" "SIMB_CIRCULO" "196491.4276,8266043.2157,1075.6573" "0.1" "" "0" "1035" "CCC" "1075.6573")
(command "_.insert" "SIMB_CIRCULO" "196497.6036,8266054.6617,1074.8235" "0.1" "" "0" "1036" "CCC" "1074.8235")
(command "_.insert" "SIMB_CIRCULO" "196494.5615,8266096.6711,1073" "0.1" "" "0" "1037" "CCC" "1073")
(command "_.insert" "SIMB_CIRCULO" "196476.549,8266055.3669,1075.38" "0.1" "" "0" "1038" "CCC" "1075.38")
(command "_.insert" "SIMB_CIRCULO" "196471.1083,8266040.5117,1076.3035" "0.1" "" "0" "1039" "CCC" "1076.3035")
(command "_.insert" "SIMB_CIRCULO" "196480.6638,8266069.098,1074.4859" "0.1" "" "0" "1040" "CCC" "1074.4859")
(command "_.insert" "SIMB_CIRCULO" "196486.604,8266077.8049,1073.5178" "0.1" "" "0" "1041" "CCC" "1073.5178")
(command "_.insert" "SIMB_CIRCULO" "196490.4749,8266085.0534,1073" "0.1" "" "0" "1042" "CCC" "1073")
(command "_.insert" "SIMB_CIRCULO" "196839.5174,8265960.5703,1053.5422" "0.1" "" "0" "1043" "CCC" "1053.5422")
(command "_.insert" "SIMB_CIRCULO" "196817.7546,8265959.3527,1055.3671" "0.1" "" "0" "1044" "CCC" "1055.3671")
(command "_.insert" "SIMB_CIRCULO" "196865.2618,8265959.9608,1050.8326" "0.1" "" "0" "1045" "CCC" "1050.8326")
(command "_.insert" "SIMB_CIRCULO" "196856.843,8265977.3928,1051.9376" "0.1" "" "0" "1046" "CCC" "1051.9376")
(command "_.insert" "SIMB_CIRCULO" "196872.7045,8265978.49,1050.1412" "0.1" "" "0" "1047" "CCC" "1050.1412")
(command "_.insert" "SIMB_CIRCULO" "196797.2567,8265969.2268,1056.9406" "0.1" "" "0" "1048" "CCC" "1056.9406")
(command "_.insert" "SIMB_CIRCULO" "196716.9323,8265971.3968,1063.4253" "0.1" "" "0" "1049" "CCC" "1063.4253")
(command "_.insert" "SIMB_CIRCULO" "196721.0807,8265952.0143,1063.4578" "0.1" "" "0" "1050" "CCC" "1063.4578")
(command "_.insert" "SIMB_CIRCULO" "196734.38,8265977.1262,1062.0056" "0.1" "" "0" "1051" "CCC" "1062.0056")
(command "_.insert" "SIMB_CIRCULO" "196776.5147,8265963.1317,1058.8015" "0.1" "" "0" "1052" "CCC" "1058.8015")
(command "_.insert" "SIMB_CIRCULO" "196754.0238,8265969.2025,1060.4265" "0.1" "" "0" "1053" "CCC" "1060.4265")
(command "_.insert" "SIMB_CIRCULO" "196838.5413,8265980.8061,1053.4298" "0.1" "" "0" "1054" "CCC" "1053.4298")
(command "_.insert" "SIMB_CIRCULO" "196750.9714,8266011.1369,1060.0104" "0.1" "" "0" "1055" "CCC" "1060.0104")
(command "_.insert" "SIMB_CIRCULO" "196714.4943,8265997.5448,1062.9749" "0.1" "" "0" "1056" "CCC" "1062.9749")
(command "_.insert" "SIMB_CIRCULO" "196772.7717,8266012.8655,1058.5599" "0.1" "" "0" "1057" "CCC" "1058.5599")
(command "_.insert" "SIMB_CIRCULO" "196812.739,8266009.0625,1055.6417" "0.1" "" "0" "1058" "CCC" "1055.6417")
(command "_.insert" "SIMB_CIRCULO" "196791.2847,8266009.5811,1057.3109" "0.1" "" "0" "1059" "CCC" "1057.3109")
(command "_.insert" "SIMB_CIRCULO" "196733.4061,8265995.3506,1061.6008" "0.1" "" "0" "1060" "CCC" "1061.6008")
(command "_.insert" "SIMB_CIRCULO" "196802.6299,8265988.021,1056.4781" "0.1" "" "0" "1061" "CCC" "1056.4781")
(command "_.insert" "SIMB_CIRCULO" "196822.9239,8265982.8784,1054.7466" "0.1" "" "0" "1062" "CCC" "1054.7466")
(command "_.insert" "SIMB_CIRCULO" "196783.3521,8265988.7524,1058.0704" "0.1" "" "0" "1063" "CCC" "1058.0704")
(command "_.insert" "SIMB_CIRCULO" "196750.7317,8265992.1811,1060.4668" "0.1" "" "0" "1064" "CCC" "1060.4668")
(command "_.insert" "SIMB_CIRCULO" "196769.3208,8265990.7029,1059.1863" "0.1" "" "0" "1065" "CCC" "1059.1863")
(command "_.insert" "SIMB_CIRCULO" "196909.3327,8265946.6649,1047" "0.1" "" "0" "1066" "CCC" "1047")
(command "_.insert" "SIMB_CIRCULO" "196891.2087,8265938.7792,1047.2534" "0.1" "" "0" "1067" "CCC" "1047.2534")
(command "_.insert" "SIMB_CIRCULO" "196932.6212,8265945.594,1047" "0.1" "" "0" "1068" "CCC" "1047")
(command "_.insert" "SIMB_CIRCULO" "196884.4837,8265961.6313,1047.8961" "0.1" "" "0" "1069" "CCC" "1047.8961")
(command "_.insert" "SIMB_CIRCULO" "196898.6275,8265956.8389,1047" "0.1" "" "0" "1070" "CCC" "1047")
(command "_.insert" "SIMB_CIRCULO" "196900.7608,8265924.4441,1047" "0.1" "" "0" "1071" "CCC" "1047")
(command "_.insert" "SIMB_CIRCULO" "196928.4345,8265901.2509,1047.4577" "0.1" "" "0" "1072" "CCC" "1047.4577")
(command "_.insert" "SIMB_CIRCULO" "196945.2918,8265899.7906,1047.1529" "0.1" "" "0" "1073" "CCC" "1047.1529")
(command "_.insert" "SIMB_CIRCULO" "196916.2543,8265910.7916,1047.4432" "0.1" "" "0" "1074" "CCC" "1047.4432")
(command "_.insert" "SIMB_CIRCULO" "196921.5158,8265932.2324,1047" "0.1" "" "0" "1075" "CCC" "1047")
(command "_.insert" "SIMB_CIRCULO" "196933.7934,8265918.6028,1047.059" "0.1" "" "0" "1076" "CCC" "1047.059")
(command "_.insert" "SIMB_CIRCULO" "196892.601,8265977.6057,1047.1058" "0.1" "" "0" "1077" "CCC" "1047.1058")
(command "_.insert" "SIMB_CIRCULO" "196780.6668,8265943.2261,1058.9185" "0.1" "" "0" "1078" "CCC" "1058.9185")
(command "_.insert" "SIMB_CIRCULO" "196800.0666,8265939.4471,1056.993" "0.1" "" "0" "1079" "CCC" "1056.993")
(command "_.insert" "SIMB_CIRCULO" "196768.3437,8265943.1042,1059.6874" "0.1" "" "0" "1080" "CCC" "1059.6874")
(command "_.insert" "SIMB_CIRCULO" "196737.0642,8265952.9895,1062.0802" "0.1" "" "0" "1081" "CCC" "1062.0802")
(command "_.insert" "SIMB_CIRCULO" "196750.408,8265947.7365,1060.9829" "0.1" "" "0" "1082" "CCC" "1060.9829")
(command "_.insert" "SIMB_CIRCULO" "196843.7056,8265934.4702,1053.3091" "0.1" "" "0" "1083" "CCC" "1053.3091")
(command "_.insert" "SIMB_CIRCULO" "196909.9845,8265964.587,1047" "0.1" "" "0" "1084" "CCC" "1047")
(command "_.insert" "SIMB_CIRCULO" "196911.2955,8265986.576,1047" "0.1" "" "0" "1085" "CCC" "1047")
(command "_.insert" "SIMB_CIRCULO" "196896.4211,8265992.5618,1047.1263" "0.1" "" "0" "1086" "CCC" "1047.1263")
(command "_.insert" "SIMB_CIRCULO" "196861.2604,8265937.6294,1051.4332" "0.1" "" "0" "1087" "CCC" "1051.4332")
(command "_.insert" "SIMB_CIRCULO" "196915.1668,8265999.9843,1046" "0.1" "" "0" "1088" "CCC" "1046")
(command "_.insert" "SIMB_CIRCULO" "196839.0091,8266003.0849,1053.5182" "0.1" "" "0" "1089" "CCC" "1053.5182")
(command "_.insert" "SIMB_CIRCULO" "196674.6401,8266029.6558,1064.5617" "0.1" "" "0" "1090" "CCC" "1064.5617")
(command "_.insert" "SIMB_CIRCULO" "196699.5281,8266026.226,1063.245" "0.1" "" "0" "1091" "CCC" "1063.245")
(command "_.insert" "SIMB_CIRCULO" "196658.8491,8266039.0876,1065.1269" "0.1" "" "0" "1092" "CCC" "1065.1269")
(command "_.insert" "SIMB_CIRCULO" "196660.2126,8266078.9024,1064.0804" "0.1" "" "0" "1093" "CCC" "1064.0804")
(command "_.insert" "SIMB_CIRCULO" "196663.1401,8266058.2943,1064.3851" "0.1" "" "0" "1094" "CCC" "1064.3851")
(command "_.insert" "SIMB_CIRCULO" "196697.9998,8266055.3907,1062.6394" "0.1" "" "0" "1095" "CCC" "1062.6394")
(command "_.insert" "SIMB_CIRCULO" "196716.0221,8266047.6738,1061.7347" "0.1" "" "0" "1096" "CCC" "1061.7347")
(command "_.insert" "SIMB_CIRCULO" "196718.4251,8266029.1531,1061.9816" "0.1" "" "0" "1097" "CCC" "1061.9816")
(command "_.insert" "SIMB_CIRCULO" "196716.1938,8266068.7668,1061.3259" "0.1" "" "0" "1098" "CCC" "1061.3259")
(command "_.insert" "SIMB_CIRCULO" "196678.6043,8266076.9982,1063.1234" "0.1" "" "0" "1099" "CCC" "1063.1234")
(command "_.insert" "SIMB_CIRCULO" "196703.149,8266069.7957,1062.0512" "0.1" "" "0" "1100" "CCC" "1062.0512")
(command "_.insert" "SIMB_CIRCULO" "196643.5634,8266081.1318,1064.6571" "0.1" "" "0" "1101" "CCC" "1064.6571")
(command "_.insert" "SIMB_CIRCULO" "196544.5273,8266107.9611,1071.0236" "0.1" "" "0" "1102" "CCC" "1071.0236")
(command "_.insert" "SIMB_CIRCULO" "196566.6399,8266102.7631,1070.4672" "0.1" "" "0" "1103" "CCC" "1070.4672")
(command "_.insert" "SIMB_CIRCULO" "196524.8764,8266115.6699,1071.1217" "0.1" "" "0" "1104" "CCC" "1071.1217")
(command "_.insert" "SIMB_CIRCULO" "196559.2576,8266112.7034,1070.2269" "0.1" "" "0" "1105" "CCC" "1070.2269")
(command "_.insert" "SIMB_CIRCULO" "196545.2012,8266115.9183,1070.5731" "0.1" "" "0" "1106" "CCC" "1070.5731")
(command "_.insert" "SIMB_CIRCULO" "196584.9647,8266097.9451,1070.2081" "0.1" "" "0" "1107" "CCC" "1070.2081")
(command "_.insert" "SIMB_CIRCULO" "196644.9056,8266096.7282,1064.4854" "0.1" "" "0" "1108" "CCC" "1064.4854")
(command "_.insert" "SIMB_CIRCULO" "196640.6455,8266061.7536,1065.3874" "0.1" "" "0" "1109" "CCC" "1065.3874")
(command "_.insert" "SIMB_CIRCULO" "196615.9718,8266099.4986,1068.6464" "0.1" "" "0" "1110" "CCC" "1068.6464")
(command "_.insert" "SIMB_CIRCULO" "196599.9138,8266096.1384,1069.7903" "0.1" "" "0" "1111" "CCC" "1069.7903")
(command "_.insert" "SIMB_CIRCULO" "196617.1774,8266090.5853,1068.7689" "0.1" "" "0" "1112" "CCC" "1068.7689")
(command "_.insert" "SIMB_CIRCULO" "196871.7793,8266047.7506,1050.9065" "0.1" "" "0" "1113" "CCC" "1050.9065")
(command "_.insert" "SIMB_CIRCULO" "196912.6255,8266033.5742,1046.0048" "0.1" "" "0" "1114" "CCC" "1046.0048")
(command "_.insert" "SIMB_CIRCULO" "196863.1648,8266031.8857,1051.73" "0.1" "" "0" "1115" "CCC" "1051.73")
(command "_.insert" "SIMB_CIRCULO" "196846.3402,8266025.7182,1052.9408" "0.1" "" "0" "1116" "CCC" "1052.9408")
(command "_.insert" "SIMB_CIRCULO" "196857.4759,8266021.9693,1052.0314" "0.1" "" "0" "1117" "CCC" "1052.0314")
(command "_.insert" "SIMB_CIRCULO" "196901.0476,8266035.3131,1047.449" "0.1" "" "0" "1118" "CCC" "1047.449")
(command "_.insert" "SIMB_CIRCULO" "196888.9949,8266008.659,1048.471" "0.1" "" "0" "1119" "CCC" "1048.471")
(command "_.insert" "SIMB_CIRCULO" "196855.6951,8266004.8095,1052.1371" "0.1" "" "0" "1120" "CCC" "1052.1371")
(command "_.insert" "SIMB_CIRCULO" "196907.9824,8266012.7789,1046" "0.1" "" "0" "1121" "CCC" "1046")
(command "_.insert" "SIMB_CIRCULO" "196886.9725,8266038.5641,1049.4232" "0.1" "" "0" "1122" "CCC" "1049.4232")
(command "_.insert" "SIMB_CIRCULO" "196882.4321,8266024.9552,1049.6106" "0.1" "" "0" "1123" "CCC" "1049.6106")
(command "_.insert" "SIMB_CIRCULO" "196853.6026,8266043.4952,1052.4364" "0.1" "" "0" "1124" "CCC" "1052.4364")
(command "_.insert" "SIMB_CIRCULO" "196798.9837,8266065.1643,1056.346" "0.1" "" "0" "1125" "CCC" "1056.346")
(command "_.insert" "SIMB_CIRCULO" "196792.8106,8266048.8385,1056.7878" "0.1" "" "0" "1126" "CCC" "1056.7878")
(command "_.insert" "SIMB_CIRCULO" "196759.4474,8266035.4981,1059.2188" "0.1" "" "0" "1127" "CCC" "1059.2188")
(command "_.insert" "SIMB_CIRCULO" "196736.2758,8266069.1097,1060.1154" "0.1" "" "0" "1128" "CCC" "1060.1154")
(command "_.insert" "SIMB_CIRCULO" "196768.0295,8266061.0498,1058.3413" "0.1" "" "0" "1129" "CCC" "1058.3413")
(command "_.insert" "SIMB_CIRCULO" "196805.7864,8266044.9266,1055.946" "0.1" "" "0" "1130" "CCC" "1055.946")
(command "_.insert" "SIMB_CIRCULO" "196837.5043,8266053.5325,1053.652" "0.1" "" "0" "1131" "CCC" "1053.652")
(command "_.insert" "SIMB_CIRCULO" "196856.0234,8266057.1605,1052.2337" "0.1" "" "0" "1132" "CCC" "1052.2337")
(command "_.insert" "SIMB_CIRCULO" "196830.2365,8266036.8241,1054.216" "0.1" "" "0" "1133" "CCC" "1054.216")
(command "_.insert" "SIMB_CIRCULO" "196802.3973,8266031.1403,1056.2602" "0.1" "" "0" "1134" "CCC" "1056.2602")
(command "_.insert" "SIMB_CIRCULO" "196816.68,8266032.8334,1055.2153" "0.1" "" "0" "1135" "CCC" "1055.2153")
(command "_.insert" "SIMB_CIRCULO" "196603.7831,8265971.2508,1070.8157" "0.1" "" "0" "1136" "CCC" "1070.8157")
(command "_.insert" "SIMB_CIRCULO" "196611.9976,8265950.6823,1071.4516" "0.1" "" "0" "1137" "CCC" "1071.4516")
(command "_.insert" "SIMB_CIRCULO" "196610.4813,8265987.1925,1069.8552" "0.1" "" "0" "1138" "CCC" "1069.8552")
(command "_.insert" "SIMB_CIRCULO" "196623.8727,8265967.6084,1070.1134" "0.1" "" "0" "1139" "CCC" "1070.1134")
(command "_.insert" "SIMB_CIRCULO" "196628.132,8265980.4764,1069.3147" "0.1" "" "0" "1140" "CCC" "1069.3147")
(command "_.insert" "SIMB_CIRCULO" "196596.2785,8265954.1273,1072.2032" "0.1" "" "0" "1141" "CCC" "1072.2032")
(command "_.insert" "SIMB_CIRCULO" "196588.8003,8265941.0348,1073.0914" "0.1" "" "0" "1142" "CCC" "1073.0914")
(command "_.insert" "SIMB_CIRCULO" "196576.1964,8265943.5152,1074.3725" "0.1" "" "0" "1143" "CCC" "1074.3725")
(command "_.insert" "SIMB_CIRCULO" "196581.1596,8265956.6657,1074.6248" "0.1" "" "0" "1144" "CCC" "1074.6248")
(command "_.insert" "SIMB_CIRCULO" "196592.6733,8265987.5261,1073.4829" "0.1" "" "0" "1145" "CCC" "1073.4829")
(command "_.insert" "SIMB_CIRCULO" "196586.7597,8265971.8232,1074.7059" "0.1" "" "0" "1146" "CCC" "1074.7059")
(command "_.insert" "SIMB_CIRCULO" "196628.8419,8265950.8903,1070.1966" "0.1" "" "0" "1147" "CCC" "1070.1966")
(command "_.insert" "SIMB_CIRCULO" "196549.5601,8266050.8008,1073.7252" "0.1" "" "0" "1148" "CCC" "1073.7252")
(command "_.insert" "SIMB_CIRCULO" "196555.2106,8266065.8551,1072.7422" "0.1" "" "0" "1149" "CCC" "1072.7422")
(command "_.insert" "SIMB_CIRCULO" "196547.229,8266034.934,1074.1882" "0.1" "" "0" "1150" "CCC" "1074.1882")
(command "_.insert" "SIMB_CIRCULO" "196560.3139,8266020.8269,1073.8586" "0.1" "" "0" "1151" "CCC" "1073.8586")
(command "_.insert" "SIMB_CIRCULO" "196542.9061,8266021.3886,1074.902" "0.1" "" "0" "1152" "CCC" "1074.902")
(command "_.insert" "SIMB_CIRCULO" "196611.6455,8266046.8404,1068.3185" "0.1" "" "0" "1153" "CCC" "1068.3185")
(command "_.insert" "SIMB_CIRCULO" "196558.7719,8266073.9359,1072.0654" "0.1" "" "0" "1154" "CCC" "1072.0654")
(command "_.insert" "SIMB_CIRCULO" "196629.4504,8265934.9826,1070.634" "0.1" "" "0" "1155" "CCC" "1070.634")
(command "_.insert" "SIMB_CIRCULO" "196573.1818,8266071.0173,1071.8802" "0.1" "" "0" "1156" "CCC" "1071.8802")
(command "_.insert" "SIMB_CIRCULO" "196599.5162,8266054.2541,1070.5967" "0.1" "" "0" "1157" "CCC" "1070.5967")
(command "_.insert" "SIMB_CIRCULO" "196586.5502,8266062.1591,1071.4601" "0.1" "" "0" "1158" "CCC" "1071.4601")
(command "_.insert" "SIMB_CIRCULO" "196528.5202,8266001.3331,1075.9774" "0.1" "" "0" "1159" "CCC" "1075.9774")
(command "_.insert" "SIMB_CIRCULO" "196519.1646,8265988.5952,1076.8874" "0.1" "" "0" "1160" "CCC" "1076.8874")
(command "_.insert" "SIMB_CIRCULO" "196529.7126,8265984.5631,1076" "0.1" "" "0" "1161" "CCC" "1076")
(command "_.insert" "SIMB_CIRCULO" "196529.9274,8265972.8915,1076.7426" "0.1" "" "0" "1162" "CCC" "1076.7426")
(command "_.insert" "SIMB_CIRCULO" "196530.6553,8265955.8004,1078.6016" "0.1" "" "0" "1163" "CCC" "1078.6016")
(command "_.insert" "SIMB_CIRCULO" "196520.2654,8265962.1889,1078.2241" "0.1" "" "0" "1164" "CCC" "1078.2241")
(command "_.insert" "SIMB_CIRCULO" "196495.6694,8265970.9046,1078.9274" "0.1" "" "0" "1165" "CCC" "1078.9274")
(command "_.insert" "SIMB_CIRCULO" "196497.4121,8265985.0171,1078.2842" "0.1" "" "0" "1166" "CCC" "1078.2842")
(command "_.insert" "SIMB_CIRCULO" "196493.8313,8265957.4976,1079.4205" "0.1" "" "0" "1167" "CCC" "1079.4205")
(command "_.insert" "SIMB_CIRCULO" "196514.2851,8265973.3512,1078.3312" "0.1" "" "0" "1168" "CCC" "1078.3312")
(command "_.insert" "SIMB_CIRCULO" "196508.5984,8265954.5651,1079.3082" "0.1" "" "0" "1169" "CCC" "1079.3082")
(command "_.insert" "SIMB_CIRCULO" "196542.4842,8265966.5278,1078.3441" "0.1" "" "0" "1170" "CCC" "1078.3441")
(command "_.insert" "SIMB_CIRCULO" "196545.6774,8266002.2115,1075.2291" "0.1" "" "0" "1171" "CCC" "1075.2291")
(command "_.insert" "SIMB_CIRCULO" "196544.4031,8265987.2772,1075.8648" "0.1" "" "0" "1172" "CCC" "1075.8648")
(command "_.insert" "SIMB_CIRCULO" "196561.7828,8265997.4841,1075.2896" "0.1" "" "0" "1173" "CCC" "1075.2896")
(command "_.insert" "SIMB_CIRCULO" "196566.075,8265944.9005,1075.8191" "0.1" "" "0" "1174" "CCC" "1075.8191")
(command "_.insert" "SIMB_CIRCULO" "196554.35,8265948.8997,1078.4136" "0.1" "" "0" "1175" "CCC" "1078.4136")
(command "_.insert" "SIMB_CIRCULO" "196554.6851,8265977.8225,1077.34" "0.1" "" "0" "1176" "CCC" "1077.34")
(command "_.insert" "SIMB_CIRCULO" "196557.1338,8265961.7096,1079" "0.1" "" "0" "1177" "CCC" "1079")
(command "_.insert" "SIMB_CIRCULO" "196544.759,8265952.6186,1079" "0.1" "" "0" "1178" "CCC" "1079")
(command "_.insert" "SIMB_CIRCULO" "196568.2428,8265971.8225,1078" "0.1" "" "0" "1179" "CCC" "1078")
(command "_.insert" "SIMB_CIRCULO" "196579.3438,8265995.8227,1075.4819" "0.1" "" "0" "1180" "CCC" "1075.4819")
(command "_.insert" "SIMB_CIRCULO" "196572.0644,8265983.5499,1077.1863" "0.1" "" "0" "1181" "CCC" "1077.1863")
(command "_.insert" "SIMB_CIRCULO" "196568.185,8266036.6851,1073.2162" "0.1" "" "0" "1182" "CCC" "1073.2162")
(command "_.insert" "SIMB_CIRCULO" "196705.1796,8265955.1636,1064.6475" "0.1" "" "0" "1183" "CCC" "1064.6475")
(command "_.insert" "SIMB_CIRCULO" "196699.2095,8265974.7848,1064.5579" "0.1" "" "0" "1184" "CCC" "1064.5579")
(command "_.insert" "SIMB_CIRCULO" "196713.8318,8265936.7524,1064.2982" "0.1" "" "0" "1185" "CCC" "1064.2982")
(command "_.insert" "SIMB_CIRCULO" "196749.1272,8265930.0069,1061.316" "0.1" "" "0" "1186" "CCC" "1061.316")
(command "_.insert" "SIMB_CIRCULO" "196729.8338,8265930.9804,1063.1502" "0.1" "" "0" "1187" "CCC" "1063.1502")
(command "_.insert" "SIMB_CIRCULO" "196693.8534,8265989.884,1064.5322" "0.1" "" "0" "1188" "CCC" "1064.5322")
(command "_.insert" "SIMB_CIRCULO" "196677.9853,8265965.8676,1066.2828" "0.1" "" "0" "1189" "CCC" "1066.2828")
(command "_.insert" "SIMB_CIRCULO" "196668.7158,8265984.547,1066.4551" "0.1" "" "0" "1190" "CCC" "1066.4551")
(command "_.insert" "SIMB_CIRCULO" "196664.9451,8266007.9355,1065.8906" "0.1" "" "0" "1191" "CCC" "1065.8906")
(command "_.insert" "SIMB_CIRCULO" "196695.5816,8266002.9125,1064.0352" "0.1" "" "0" "1192" "CCC" "1064.0352")
(command "_.insert" "SIMB_CIRCULO" "196679.2421,8266000.244,1065.9187" "0.1" "" "0" "1193" "CCC" "1065.9187")
(command "_.insert" "SIMB_CIRCULO" "196766.4717,8265926.2101,1059.9217" "0.1" "" "0" "1194" "CCC" "1059.9217")
(command "_.insert" "SIMB_CIRCULO" "196887.4712,8265912.5612,1048.5207" "0.1" "" "0" "1195" "CCC" "1048.5207")
(command "_.insert" "SIMB_CIRCULO" "196873.9269,8265913.8268,1049.9849" "0.1" "" "0" "1196" "CCC" "1049.9849")
(command "_.insert" "SIMB_CIRCULO" "196896.1435,8265903.9941,1048.1533" "0.1" "" "0" "1197" "CCC" "1048.1533")
(command "_.insert" "SIMB_CIRCULO" "196933.404,8265887.6214,1047.4702" "0.1" "" "0" "1198" "CCC" "1047.4702")
(command "_.insert" "SIMB_CIRCULO" "196913.4285,8265890.1526,1047.8959" "0.1" "" "0" "1199" "CCC" "1047.8959")
(command "_.insert" "SIMB_CIRCULO" "196873.1473,8265896.7899,1050.1492" "0.1" "" "0" "1200" "CCC" "1050.1492")
(command "_.insert" "SIMB_CIRCULO" "196803.6527,8265920.8524,1056.8073" "0.1" "" "0" "1201" "CCC" "1056.8073")
(command "_.insert" "SIMB_CIRCULO" "196784.7906,8265923.4842,1058.9689" "0.1" "" "0" "1202" "CCC" "1058.9689")
(command "_.insert" "SIMB_CIRCULO" "196821.7767,8265919.8789,1055.2294" "0.1" "" "0" "1203" "CCC" "1055.2294")
(command "_.insert" "SIMB_CIRCULO" "196856.1926,8265916.3581,1052.0692" "0.1" "" "0" "1204" "CCC" "1052.0692")
(command "_.insert" "SIMB_CIRCULO" "196839.3161,8265913.5509,1053.6359" "0.1" "" "0" "1205" "CCC" "1053.6359")
(command "_.insert" "SIMB_CIRCULO" "196604.5366,8266019.0567,1069.1177" "0.1" "" "0" "1206" "CCC" "1069.1177")
(command "_.insert" "SIMB_CIRCULO" "196603.9827,8266006.1055,1069.3011" "0.1" "" "0" "1207" "CCC" "1069.3011")
(command "_.insert" "SIMB_CIRCULO" "196593.3466,8266000.9029,1072.3763" "0.1" "" "0" "1208" "CCC" "1072.3763")
(command "_.insert" "SIMB_CIRCULO" "196623.7188,8266026.4967,1067" "0.1" "" "0" "1209" "CCC" "1067")
(command "_.insert" "SIMB_CIRCULO" "196613.8583,8266033.6918,1067.2264" "0.1" "" "0" "1210" "CCC" "1067.2264")
(command "_.insert" "SIMB_CIRCULO" "196598.9892,8265994.0344,1071.4259" "0.1" "" "0" "1211" "CCC" "1071.4259")
(command "_.insert" "SIMB_CIRCULO" "196590.3436,8266041.3343,1071.4315" "0.1" "" "0" "1212" "CCC" "1071.4315")
(command "_.insert" "SIMB_CIRCULO" "196575.165,8266051.8502,1072.4192" "0.1" "" "0" "1213" "CCC" "1072.4192")
(command "_.insert" "SIMB_CIRCULO" "196581.8125,8266022.2949,1073.1662" "0.1" "" "0" "1214" "CCC" "1073.1662")
(command "_.insert" "SIMB_CIRCULO" "196592.3416,8266008.2032,1071.5948" "0.1" "" "0" "1215" "CCC" "1071.5948")
(command "_.insert" "SIMB_CIRCULO" "196575.5011,8266009.0888,1074.0704" "0.1" "" "0" "1216" "CCC" "1074.0704")
(command "_.insert" "SIMB_CIRCULO" "196620.9485,8266012.9644,1069" "0.1" "" "0" "1217" "CCC" "1069")
(command "_.insert" "SIMB_CIRCULO" "196676.3296,8265950.8363,1066.7083" "0.1" "" "0" "1218" "CCC" "1066.7083")
(command "_.insert" "SIMB_CIRCULO" "196679.1781,8265930.7186,1067.3701" "0.1" "" "0" "1219" "CCC" "1067.3701")
(command "_.insert" "SIMB_CIRCULO" "196694.108,8265928.2653,1066.1009" "0.1" "" "0" "1220" "CCC" "1066.1009")
(command "_.insert" "SIMB_CIRCULO" "196649.4214,8265998.5878,1066.9644" "0.1" "" "0" "1221" "CCC" "1066.9644")
(command "_.insert" "SIMB_CIRCULO" "196651.484,8265974.741,1066.9813" "0.1" "" "0" "1222" "CCC" "1066.9813")
(command "_.insert" "SIMB_CIRCULO" "196669.5522,8265939.6489,1067.7438" "0.1" "" "0" "1223" "CCC" "1067.7438")
(command "_.insert" "SIMB_CIRCULO" "196628.8148,8266001.5629,1068.8008" "0.1" "" "0" "1224" "CCC" "1068.8008")
(command "_.insert" "SIMB_CIRCULO" "196633.0249,8266013.0751,1067.5727" "0.1" "" "0" "1225" "CCC" "1067.5727")
(command "_.insert" "SIMB_CIRCULO" "196617.6246,8266000.1916,1069.2676" "0.1" "" "0" "1226" "CCC" "1069.2676")
(command "_.insert" "SIMB_CIRCULO" "196656.7832,8265951.7195,1067" "0.1" "" "0" "1227" "CCC" "1067")
(command "_.insert" "SIMB_CIRCULO" "196646.5681,8265942.2004,1069.0544" "0.1" "" "0" "1228" "CCC" "1069.0544")
(setvar "cmdecho" olcmdecho)
(setvar "clayer" oldlayer)
(princ)
)
(princ "\nDigite 'recanto' para iniciar")
