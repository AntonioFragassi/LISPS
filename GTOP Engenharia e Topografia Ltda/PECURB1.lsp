;; Coloca os blocos segundo a descrição 
(defun c:PECURB1(/)
(princ "********* Espere um pouco - processando dados  ***********")
(setq olcmdecho (getvar "cmdecho"))
(setvar "cmdecho" 0)
(command "_.insert" "INCRA_vertice_P" "197926.93,8265819.832,1066.33" "0.01" "" "0" "1=766" "")
(command "_.insert" "INCRA_vertice_P" "197450.674,8266193.6523,1064.54" "0.01" "" "0" "2=pec\cer" "")
(command "_.insert" "INCRA_vertice_P" "197534.2909,8266165.7896,1064.93" "0.01" "" "0" "3=pec\pcat" "")
(command "_.insert" "INCRA_vertice_P" "197597.2395,8266144.3242,1064.23" "0.01" "" "0" "4=pec\guarita" "")
(command "_.insert" "INCRA_vertice_P" "197597.0426,8266111.0159,1066.31" "0.01" "" "0" "5=pecz" "")
(command "_.insert" "INCRA_vertice_P" "197604.5509,8266125.8728,1064.63" "0.01" "" "0" "6=pec\pcat" "")
(command "_.insert" "INCRA_vertice_P" "197666.7295,8266113.0967,1064.22" "0.01" "" "0" "7=pec\cer" "")
(command "_.insert" "INCRA_vertice_P" "197648.8624,8266081.0773,1066.36" "0.01" "" "0" "8=pecz" "")
(command "_.insert" "INCRA_vertice_P" "197891.8953,8266782.9906,1046.34" "0.01" "" "0" "9=pec\alb" "")
(command "_.insert" "INCRA_vertice_P" "197451.1909,8266806.0977,1047.75" "0.01" "" "0" "10=pec\cer" "")
(command "_.insert" "INCRA_vertice_P" "197496.8443,8266953.1962,1044.7" "0.01" "" "0" "11=pec\cer" "")
(command "_.insert" "INCRA_vertice_P" "197684.2658,8266995.1278,1043.37" "0.01" "" "0" "12=pec\alb" "")
(command "_.insert" "INCRA_vertice_P" "197707.2738,8266040.1652,1066.41" "0.01" "" "0" "13=pecz" "")
(command "_.insert" "INCRA_vertice_P" "197756.5523,8266998.0581,1042.11" "0.01" "" "0" "14=pec\mfi" "")
(command "_.insert" "INCRA_vertice_P" "197802.292,8266946.761,1041.79" "0.01" "" "0" "15=pec\mfi" "")
(command "_.insert" "INCRA_vertice_P" "197887.501,8266922.903,1043" "0.01" "" "0" "16=pec\piscina" "")
(command "_.insert" "INCRA_vertice_P" "198009.6001,8266997.7755,1034.77" "0.01" "" "0" "17=pec\alb" "")
(command "_.insert" "INCRA_vertice_P" "198042.7111,8266971.231,1034.38" "0.01" "" "0" "18=pec\alb" "")
(command "_.insert" "INCRA_vertice_P" "197999.6754,8266864.1141,1041.23" "0.01" "" "0" "19=pecz" "")
(command "_.insert" "INCRA_vertice_P" "198017.3511,8266852.8268,1041.14" "0.01" "" "0" "20=pec\pcat" "")
(command "_.insert" "INCRA_vertice_P" "197947.0945,8266737.4889,1046.13" "0.01" "" "0" "21=pec\pcat" "")
(command "_.insert" "INCRA_vertice_P" "197941.3348,8266741.0251,1046.07" "0.01" "" "0" "22=pecz" "")
(command "_.insert" "INCRA_vertice_P" "197879.5134,8266634.029,1049.33" "0.01" "" "0" "23=pecz" "")
(command "_.insert" "INCRA_vertice_P" "197721.3603,8266059.2508,1064.91" "0.01" "" "0" "24=pec\pcat" "")
(command "_.insert" "INCRA_vertice_P" "197882.3975,8266624.6461,1049.67" "0.01" "" "0" "25=pec\pcat" "")
(command "_.insert" "INCRA_vertice_P" "197815.275,8266507.7563,1053.26" "0.01" "" "0" "26=pec\pcat" "")
(command "_.insert" "INCRA_vertice_P" "197811.0414,8266509.9995,1052.88" "0.01" "" "0" "27=pecz" "")
(command "_.insert" "INCRA_vertice_P" "197744.7449,8266397.7154,1056.09" "0.01" "" "0" "28=pecz" "")
(command "_.insert" "INCRA_vertice_P" "197750.5044,8266394.8256,1056.45" "0.01" "" "0" "29=pec\pcat" "")
(command "_.insert" "INCRA_vertice_P" "197685.6553,8266281.5795,1059.83" "0.01" "" "0" "30=pec\pcat" "")
(command "_.insert" "INCRA_vertice_P" "197678.8807,8266284.5096,1059.41" "0.01" "" "0" "31=pecz" "")
(command "_.insert" "INCRA_vertice_P" "197367.6774,8266187.4792,1065.12" "0.01" "" "0" "32=pecz" "")
(command "_.insert" "INCRA_vertice_P" "197368.5665,8266208.3107,1064.22" "0.01" "" "0" "33=pec\pcat" "")
(command "_.insert" "INCRA_vertice_P" "197446.1994,8266170.0887,1066.19" "0.01" "" "0" "34=pecz" "")
(setvar "cmdecho" olcmdecho)
(setvar "clayer" oldlayer)
(princ)
)
(princ "\nDigite 'PECURB1' para iniciar")
